L2TP-MIB DEFINITIONS ::= BEGIN

   IMPORTS
           Integer32, Unsigned32, Counter32, Gauge32,
           Counter64, transmission, MODULE-IDENTITY,
           OBJECT-TYPE, NOTIFICATION-TYPE
               FROM SNMPv2-SMI
           TEXTUAL-CONVENTION, RowStatus, TruthValue,
           StorageType
               FROM SNMPv2-TC
           SnmpAdminString
               FROM SNMP-FRAMEWORK-MIB
           OBJECT-GROUP, MODULE-COMPLIANCE, NOTIFICATION-GROUP
               FROM SNMPv2-CONF
           InterfaceIndex
               FROM IF-MIB;

   l2tp    MODULE-IDENTITY
           LAST-UPDATED    "200208230000Z" -- 23 August 2002
           ORGANIZATION    "IETF L2TP Working Group"




           ::= { transmission 95 }


   L2tpMilliSeconds ::=  TEXTUAL-CONVENTION
           DISPLAY-HINT    "d-3"
           STATUS          current
           SYNTAX          Integer32 (0..2147483646)






   l2tpNotifications   OBJECT IDENTIFIER  ::= { l2tp 0 }
   l2tpObjects         OBJECT IDENTIFIER  ::= { l2tp 1 }
   l2tpTransports      OBJECT IDENTIFIER  ::= { l2tp 3 }
   l2tpConformance     OBJECT IDENTIFIER  ::= { l2tp 4 }

   l2tpScalar          OBJECT IDENTIFIER  ::= { l2tpObjects 1 }
   l2tpConfig          OBJECT IDENTIFIER  ::= { l2tpScalar 1 }
   l2tpStats           OBJECT IDENTIFIER  ::= { l2tpScalar 2 }


   l2tpTransportIpUdp  OBJECT IDENTIFIER  ::= { l2tpTransports 1 }
   l2tpIpUdpObjects    OBJECT IDENTIFIER  ::= { l2tpTransportIpUdp 1 }
   l2tpIpUdpTraps      OBJECT IDENTIFIER  ::= { l2tpTransportIpUdp 2 }


   l2tpAdminState          OBJECT-TYPE
           SYNTAX          INTEGER {
                               enabled(1),
                               disabled(2)
                           }
           MAX-ACCESS      read-write
           STATUS          current
           ::= { l2tpConfig 1 }

   l2tpDrainTunnels        OBJECT-TYPE
           SYNTAX          TruthValue
           MAX-ACCESS      read-write
           STATUS          current





           ::= { l2tpConfig 2 }


   l2tpProtocolVersions    OBJECT-TYPE
           SYNTAX          OCTET STRING (SIZE(2..256))
           MAX-ACCESS      read-only
           STATUS          current
           ::= { l2tpStats 1 }

   l2tpVendorName          OBJECT-TYPE
           SYNTAX          SnmpAdminString
           MAX-ACCESS      read-only
           STATUS          current
           ::= { l2tpStats 2 }

   l2tpFirmwareRev         OBJECT-TYPE
           SYNTAX          Integer32
           MAX-ACCESS      read-only





           STATUS          current
           ::= { l2tpStats 3 }

   l2tpDrainingTunnels     OBJECT-TYPE
           SYNTAX          TruthValue
           MAX-ACCESS      read-only
           STATUS          current
           ::= { l2tpStats 4 }


   l2tpDomainConfigTable   OBJECT-TYPE
           SYNTAX          SEQUENCE OF L2tpDomainConfigEntry
           MAX-ACCESS      not-accessible
           STATUS          current
           ::= { l2tpObjects 2 }

   l2tpDomainConfigEntry   OBJECT-TYPE
           SYNTAX          L2tpDomainConfigEntry
           MAX-ACCESS      not-accessible
           STATUS          current
           INDEX { l2tpDomainConfigId }
           ::= { l2tpDomainConfigTable 1 }

   L2tpDomainConfigEntry ::=
           SEQUENCE {
               l2tpDomainConfigId
                   SnmpAdminString,
               l2tpDomainConfigAdminState





                   INTEGER,
               l2tpDomainConfigDrainTunnels
                   TruthValue,
               l2tpDomainConfigAuth
                   INTEGER,
               l2tpDomainConfigSecret
                   SnmpAdminString,
               l2tpDomainConfigTunnelSecurity
                   INTEGER,
               l2tpDomainConfigTunnelHelloInt
                   Integer32,
               l2tpDomainConfigTunnelIdleTO
                   Integer32,
               l2tpDomainConfigControlRWS
                   Integer32,
               l2tpDomainConfigControlMaxRetx
                   Integer32,
               l2tpDomainConfigControlMaxRetxTO
                   Integer32,
               l2tpDomainConfigPayloadSeq
                   INTEGER,
               l2tpDomainConfigReassemblyTO
                   L2tpMilliSeconds,
               l2tpDomainConfigProxyPPPAuth
                   TruthValue,
               l2tpDomainConfigStorageType
                   StorageType,
               l2tpDomainConfigStatus
                   RowStatus
           }

   l2tpDomainConfigId OBJECT-TYPE
           SYNTAX          SnmpAdminString (SIZE (1..80))
           MAX-ACCESS      not-accessible
           STATUS          current
           ::= { l2tpDomainConfigEntry 1 }

   l2tpDomainConfigAdminState OBJECT-TYPE
           SYNTAX          INTEGER {
                               enabled(1),
                               disabled(2)
                           }
           MAX-ACCESS      read-create
           STATUS          current
           DEFVAL { enabled }
           ::= { l2tpDomainConfigEntry 2 }

   l2tpDomainConfigDrainTunnels OBJECT-TYPE
           SYNTAX          TruthValue
           MAX-ACCESS      read-create
           STATUS          current
           DEFVAL { false }
           ::= { l2tpDomainConfigEntry 3 }

   l2tpDomainConfigAuth OBJECT-TYPE
           SYNTAX          INTEGER {
                               none(1),
                               simple(2),
                               challenge(3)
                           }
           MAX-ACCESS      read-create
           STATUS          current
           DEFVAL { none }
           ::= { l2tpDomainConfigEntry 4 }

   l2tpDomainConfigSecret  OBJECT-TYPE
           SYNTAX          SnmpAdminString (SIZE (0..255))
           MAX-ACCESS      read-create
           STATUS          current
           ::= { l2tpDomainConfigEntry 5 }

   l2tpDomainConfigTunnelSecurity OBJECT-TYPE
           SYNTAX          INTEGER {
                               none(1),
                               other(2),
                               ipSec(3)
                           }
           MAX-ACCESS      read-create
           STATUS          current
           DEFVAL { none }
           ::= { l2tpDomainConfigEntry 6 }

   l2tpDomainConfigTunnelHelloInt OBJECT-TYPE
           SYNTAX          Integer32 (0..3600)
           UNITS           "seconds"
           MAX-ACCESS      read-create
           STATUS          current
           DEFVAL { 60 }
           ::= { l2tpDomainConfigEntry 7 }

   l2tpDomainConfigTunnelIdleTO OBJECT-TYPE
           SYNTAX          Integer32 (-1..86400)
           UNITS           "seconds"
           MAX-ACCESS      read-create
           STATUS          current
           DEFVAL { 0 }
           ::= { l2tpDomainConfigEntry 8 }

   l2tpDomainConfigControlRWS OBJECT-TYPE
           SYNTAX          Integer32 (1..65535)
           MAX-ACCESS      read-create
           STATUS          current
           DEFVAL { 4 }
           ::= { l2tpDomainConfigEntry 9 }

   l2tpDomainConfigControlMaxRetx OBJECT-TYPE
           SYNTAX          Integer32 (0..32)
           MAX-ACCESS      read-create
           STATUS          current
           DEFVAL { 5 }
           ::= { l2tpDomainConfigEntry 10 }

   l2tpDomainConfigControlMaxRetxTO OBJECT-TYPE
           SYNTAX          Integer32 (1..32)
           UNITS           "seconds"
           MAX-ACCESS      read-create
           STATUS          current
           DEFVAL { 16 }
           ::= { l2tpDomainConfigEntry 11 }

   l2tpDomainConfigPayloadSeq OBJECT-TYPE
           SYNTAX          INTEGER {
                               onDemand(1),
                               never(2),
                               always(3)
                           }
           MAX-ACCESS      read-create
           STATUS          current
           DEFVAL { onDemand }
           ::= { l2tpDomainConfigEntry 12 }

   l2tpDomainConfigReassemblyTO OBJECT-TYPE
           SYNTAX          L2tpMilliSeconds
           MAX-ACCESS      read-create
           STATUS          current
           DEFVAL { 0 }
           ::= { l2tpDomainConfigEntry 13 }

   l2tpDomainConfigProxyPPPAuth OBJECT-TYPE
           SYNTAX          TruthValue
           MAX-ACCESS      read-create
           STATUS          current
           DEFVAL { true }
           ::= { l2tpDomainConfigEntry 14 }

   l2tpDomainConfigStorageType  OBJECT-TYPE
           SYNTAX          StorageType
           MAX-ACCESS      read-create
           STATUS          current
           ::= { l2tpDomainConfigEntry 15 }

   l2tpDomainConfigStatus  OBJECT-TYPE
           SYNTAX          RowStatus
           MAX-ACCESS      read-create
           STATUS          current
           ::= { l2tpDomainConfigEntry 16 }


   l2tpDomainStatsTable    OBJECT-TYPE
           SYNTAX          SEQUENCE OF L2tpDomainStatsEntry
           MAX-ACCESS      not-accessible
           STATUS          current
           ::= { l2tpObjects 3 }

   l2tpDomainStatsEntry    OBJECT-TYPE
           SYNTAX          L2tpDomainStatsEntry
           MAX-ACCESS      not-accessible
           STATUS          current
           AUGMENTS { l2tpDomainConfigEntry }





           ::= { l2tpDomainStatsTable 1 }

   L2tpDomainStatsEntry ::=
           SEQUENCE {
               l2tpDomainStatsTotalTunnels
                   Counter32,
               l2tpDomainStatsFailedTunnels
                   Counter32,
               l2tpDomainStatsFailedAuths
                   Counter32,
               l2tpDomainStatsActiveTunnels
                   Gauge32,
               l2tpDomainStatsTotalSessions
                   Counter32,
               l2tpDomainStatsFailedSessions
                   Counter32,
               l2tpDomainStatsActiveSessions
                   Gauge32,
               l2tpDomainStatsDrainingTunnels
                   TruthValue,
               l2tpDomainStatsControlRxOctets
                   Counter32,
               l2tpDomainStatsControlRxPkts
                   Counter32,
               l2tpDomainStatsControlTxOctets
                   Counter32,
               l2tpDomainStatsControlTxPkts
                   Counter32,
               l2tpDomainStatsPayloadRxOctets
                   Counter32,
               l2tpDomainStatsPayloadRxPkts
                   Counter32,
               l2tpDomainStatsPayloadRxDiscs
                   Counter32,
               l2tpDomainStatsPayloadTxOctets
                   Counter32,
               l2tpDomainStatsPayloadTxPkts
                   Counter32,
               l2tpDomainStatsControlHCRxOctets
                   Counter64,
               l2tpDomainStatsControlHCRxPkts
                   Counter64,
               l2tpDomainStatsControlHCTxOctets
                   Counter64,
               l2tpDomainStatsControlHCTxPkts
                   Counter64,
               l2tpDomainStatsPayloadHCRxOctets
                   Counter64,





               l2tpDomainStatsPayloadHCRxPkts
                   Counter64,
               l2tpDomainStatsPayloadHCRxDiscs
                   Counter64,
               l2tpDomainStatsPayloadHCTxOctets
                   Counter64,
               l2tpDomainStatsPayloadHCTxPkts
                   Counter64
           }

   l2tpDomainStatsTotalTunnels OBJECT-TYPE
           SYNTAX          Counter32
           MAX-ACCESS      read-only
           STATUS          current
           ::= { l2tpDomainStatsEntry 1 }

   l2tpDomainStatsFailedTunnels OBJECT-TYPE
           SYNTAX          Counter32
           MAX-ACCESS      read-only
           STATUS          current
           ::= { l2tpDomainStatsEntry 2 }

   l2tpDomainStatsFailedAuths OBJECT-TYPE
           SYNTAX          Counter32
           MAX-ACCESS      read-only
           STATUS          current
           ::= { l2tpDomainStatsEntry 3 }

   l2tpDomainStatsActiveTunnels OBJECT-TYPE
           SYNTAX          Gauge32
           MAX-ACCESS      read-only
           STATUS          current





           ::= { l2tpDomainStatsEntry 4 }

   l2tpDomainStatsTotalSessions OBJECT-TYPE
           SYNTAX          Counter32
           MAX-ACCESS      read-only
           STATUS          current
           ::= { l2tpDomainStatsEntry 5 }

   l2tpDomainStatsFailedSessions OBJECT-TYPE
           SYNTAX          Counter32
           MAX-ACCESS      read-only
           STATUS          current
           ::= { l2tpDomainStatsEntry 6 }

   l2tpDomainStatsActiveSessions OBJECT-TYPE
           SYNTAX          Gauge32
           MAX-ACCESS      read-only
           STATUS          current
           ::= { l2tpDomainStatsEntry 7 }

   l2tpDomainStatsDrainingTunnels OBJECT-TYPE
           SYNTAX          TruthValue
           MAX-ACCESS      read-only
           STATUS          current
           ::= { l2tpDomainStatsEntry 8 }

   l2tpDomainStatsControlRxOctets OBJECT-TYPE
           SYNTAX          Counter32
           MAX-ACCESS      read-only
           STATUS          current





           ::= { l2tpDomainStatsEntry 9 }

   l2tpDomainStatsControlRxPkts OBJECT-TYPE
           SYNTAX          Counter32
           MAX-ACCESS      read-only
           STATUS          current
           ::= { l2tpDomainStatsEntry 10 }

   l2tpDomainStatsControlTxOctets OBJECT-TYPE
           SYNTAX          Counter32
           MAX-ACCESS      read-only
           STATUS          current
           ::= { l2tpDomainStatsEntry 11 }

   l2tpDomainStatsControlTxPkts OBJECT-TYPE
           SYNTAX          Counter32
           MAX-ACCESS      read-only
           STATUS          current
           ::= { l2tpDomainStatsEntry 12 }

   l2tpDomainStatsPayloadRxOctets OBJECT-TYPE
           SYNTAX          Counter32
           MAX-ACCESS      read-only
           STATUS          current
           ::= { l2tpDomainStatsEntry 13 }

   l2tpDomainStatsPayloadRxPkts OBJECT-TYPE
           SYNTAX          Counter32
           MAX-ACCESS      read-only
           STATUS          current
           ::= { l2tpDomainStatsEntry 14 }





   l2tpDomainStatsPayloadRxDiscs OBJECT-TYPE
           SYNTAX          Counter32
           MAX-ACCESS      read-only
           STATUS          current
           ::= { l2tpDomainStatsEntry 15 }

   l2tpDomainStatsPayloadTxOctets OBJECT-TYPE
           SYNTAX          Counter32
           MAX-ACCESS      read-only
           STATUS          current
           ::= { l2tpDomainStatsEntry 16 }

   l2tpDomainStatsPayloadTxPkts OBJECT-TYPE
           SYNTAX          Counter32
           MAX-ACCESS      read-only
           STATUS          current
           ::= { l2tpDomainStatsEntry 17 }


   l2tpDomainStatsControlHCRxOctets OBJECT-TYPE
           SYNTAX          Counter64
           MAX-ACCESS      read-only
           STATUS          current
           ::= { l2tpDomainStatsEntry 18 }

   l2tpDomainStatsControlHCRxPkts OBJECT-TYPE
           SYNTAX          Counter64





           MAX-ACCESS      read-only
           STATUS          current
           ::= { l2tpDomainStatsEntry 19 }

   l2tpDomainStatsControlHCTxOctets OBJECT-TYPE
           SYNTAX          Counter64
           MAX-ACCESS      read-only
           STATUS          current
           ::= { l2tpDomainStatsEntry 20 }

   l2tpDomainStatsControlHCTxPkts OBJECT-TYPE
           SYNTAX          Counter64
           MAX-ACCESS      read-only
           STATUS          current
           ::= { l2tpDomainStatsEntry 21 }

   l2tpDomainStatsPayloadHCRxOctets OBJECT-TYPE
           SYNTAX          Counter64
           MAX-ACCESS      read-only
           STATUS          current
           ::= { l2tpDomainStatsEntry 22 }

   l2tpDomainStatsPayloadHCRxPkts OBJECT-TYPE
           SYNTAX          Counter64
           MAX-ACCESS      read-only
           STATUS          current
           ::= { l2tpDomainStatsEntry 23 }

   l2tpDomainStatsPayloadHCRxDiscs OBJECT-TYPE
           SYNTAX          Counter64
           MAX-ACCESS      read-only
           STATUS          current
           ::= { l2tpDomainStatsEntry 24 }

   l2tpDomainStatsPayloadHCTxOctets OBJECT-TYPE
           SYNTAX          Counter64
           MAX-ACCESS      read-only
           STATUS          current
           ::= { l2tpDomainStatsEntry 25 }

   l2tpDomainStatsPayloadHCTxPkts OBJECT-TYPE
           SYNTAX          Counter64
           MAX-ACCESS      read-only
           STATUS          current
           ::= { l2tpDomainStatsEntry 26 }


   l2tpTunnelConfigTable   OBJECT-TYPE
           SYNTAX          SEQUENCE OF L2tpTunnelConfigEntry
           MAX-ACCESS      not-accessible
           STATUS          current
           ::= { l2tpObjects 4 }

   l2tpTunnelConfigEntry   OBJECT-TYPE
           SYNTAX          L2tpTunnelConfigEntry
           MAX-ACCESS      not-accessible
           STATUS          current
           INDEX { l2tpTunnelConfigIfIndex }
           ::= { l2tpTunnelConfigTable 1 }

   L2tpTunnelConfigEntry ::=
           SEQUENCE {
               l2tpTunnelConfigIfIndex
                   InterfaceIndex,
               l2tpTunnelConfigDomainId
                   SnmpAdminString,
               l2tpTunnelConfigAuth
                   INTEGER,
               l2tpTunnelConfigSecret
                   SnmpAdminString,
               l2tpTunnelConfigSecurity
                   INTEGER,
               l2tpTunnelConfigHelloInterval
                   Integer32,
               l2tpTunnelConfigIdleTimeout
                   Integer32,
               l2tpTunnelConfigControlRWS
                   Integer32,
               l2tpTunnelConfigControlMaxRetx
                   Integer32,
               l2tpTunnelConfigControlMaxRetxTO
                   Integer32,
               l2tpTunnelConfigPayloadSeq
                   INTEGER,
               l2tpTunnelConfigReassemblyTO
                   L2tpMilliSeconds,
               l2tpTunnelConfigTransport
                   INTEGER,
               l2tpTunnelConfigDrainTunnel
                   TruthValue,
               l2tpTunnelConfigProxyPPPAuth
                   TruthValue
           }

   l2tpTunnelConfigIfIndex OBJECT-TYPE
           SYNTAX          InterfaceIndex
           MAX-ACCESS      not-accessible
           STATUS          current





           ::= { l2tpTunnelConfigEntry 1 }

   l2tpTunnelConfigDomainId OBJECT-TYPE
           SYNTAX          SnmpAdminString (SIZE (1..80))
           MAX-ACCESS      read-write
           STATUS          current
           ::= { l2tpTunnelConfigEntry 2 }

   l2tpTunnelConfigAuth OBJECT-TYPE
           SYNTAX          INTEGER {
                               none(1),
                               simple(2),
                               challenge(3)
                           }
           MAX-ACCESS      read-write
           STATUS          current
           DEFVAL { none }
           ::= { l2tpTunnelConfigEntry 3 }

   l2tpTunnelConfigSecret  OBJECT-TYPE
           SYNTAX          SnmpAdminString (SIZE (0..255))
           MAX-ACCESS      read-write
           STATUS          current
           ::= { l2tpTunnelConfigEntry 4 }

   l2tpTunnelConfigSecurity OBJECT-TYPE
           SYNTAX          INTEGER {
                               none(1),
                               other(2),
                               ipsec(3)
                           }
           MAX-ACCESS      read-write
           STATUS          current
           DEFVAL { none }
           ::= { l2tpTunnelConfigEntry 5 }

   l2tpTunnelConfigHelloInterval OBJECT-TYPE
           SYNTAX          Integer32  (0..3600)
           UNITS           "seconds"
           MAX-ACCESS      read-write
           STATUS          current
           DEFVAL { 60 }
           ::= { l2tpTunnelConfigEntry 6 }

   l2tpTunnelConfigIdleTimeout OBJECT-TYPE
           SYNTAX          Integer32 (-1..86400)
           UNITS           "seconds"
           MAX-ACCESS      read-write
           STATUS          current
           DEFVAL { 0 }
           ::= { l2tpTunnelConfigEntry 7 }

   l2tpTunnelConfigControlRWS OBJECT-TYPE
           SYNTAX          Integer32 (1..65535)
           MAX-ACCESS      read-write
           STATUS          current
           DEFVAL { 4 }
           ::= { l2tpTunnelConfigEntry 8 }

   l2tpTunnelConfigControlMaxRetx OBJECT-TYPE
           SYNTAX          Integer32 (0..32)
           MAX-ACCESS      read-write
           STATUS          current
           DEFVAL { 5 }
           ::= { l2tpTunnelConfigEntry 9 }

   l2tpTunnelConfigControlMaxRetxTO OBJECT-TYPE
           SYNTAX          Integer32 (1..32)
           UNITS           "seconds"
           MAX-ACCESS      read-write
           STATUS          current
           DEFVAL { 16 }
           ::= { l2tpTunnelConfigEntry 10 }

   l2tpTunnelConfigPayloadSeq OBJECT-TYPE
           SYNTAX          INTEGER {
                               onDemand(1),
                               never(2),
                               always(3)
                           }
           MAX-ACCESS      read-write
           STATUS          current
           DEFVAL { onDemand }
           ::= { l2tpTunnelConfigEntry 11 }

   l2tpTunnelConfigReassemblyTO OBJECT-TYPE
           SYNTAX          L2tpMilliSeconds
           MAX-ACCESS      read-write
           STATUS          current
           DEFVAL { 0 }
           ::= { l2tpTunnelConfigEntry 12 }






   l2tpTunnelConfigTransport OBJECT-TYPE
           SYNTAX          INTEGER {
                              other(1),
                              none(2),
                              udpIp(3),
                              frameRelay(4),
                              atm(5)
                           }
           MAX-ACCESS      read-write
           STATUS          current
           ::= { l2tpTunnelConfigEntry 13 }

   l2tpTunnelConfigDrainTunnel OBJECT-TYPE
           SYNTAX          TruthValue
           MAX-ACCESS      read-write
           STATUS          current
           DEFVAL { false }
           ::= { l2tpTunnelConfigEntry 14 }

   l2tpTunnelConfigProxyPPPAuth OBJECT-TYPE
           SYNTAX          TruthValue
           MAX-ACCESS      read-write
           STATUS          current





           DEFVAL { true }
           ::= { l2tpTunnelConfigEntry 15 }



   l2tpTunnelStatsTable    OBJECT-TYPE
           SYNTAX          SEQUENCE OF L2tpTunnelStatsEntry
           MAX-ACCESS      not-accessible
           STATUS          current
           ::= { l2tpObjects 5 }

   l2tpTunnelStatsEntry    OBJECT-TYPE
           SYNTAX          L2tpTunnelStatsEntry
           MAX-ACCESS      not-accessible
           STATUS          current
           AUGMENTS { l2tpTunnelConfigEntry }
           ::= { l2tpTunnelStatsTable 1 }

   L2tpTunnelStatsEntry ::=
           SEQUENCE {
               l2tpTunnelStatsLocalTID
                   Integer32,
               l2tpTunnelStatsRemoteTID
                   Integer32,
               l2tpTunnelStatsState
                   INTEGER,
               l2tpTunnelStatsInitiated
                   INTEGER,
               l2tpTunnelStatsRemoteHostName
                   SnmpAdminString,
               l2tpTunnelStatsRemoteVendorName
                   SnmpAdminString,
               l2tpTunnelStatsRemoteFirmwareRev
                   Integer32,
               l2tpTunnelStatsRemoteProtocolVer
                   OCTET STRING,





               l2tpTunnelStatsInitialRemoteRWS
                   Integer32,
               l2tpTunnelStatsBearerCaps
                   INTEGER,
               l2tpTunnelStatsFramingCaps
                   INTEGER,
               l2tpTunnelStatsControlRxPkts
                   Counter32,
               l2tpTunnelStatsControlRxZLB
                   Counter32,
               l2tpTunnelStatsControlOutOfSeq
                   Counter32,
               l2tpTunnelStatsControlOutOfWin
                   Counter32,
               l2tpTunnelStatsControlTxPkts
                   Counter32,
               l2tpTunnelStatsControlTxZLB
                   Counter32,
               l2tpTunnelStatsControlAckTO
                   Counter32,
               l2tpTunnelStatsCurrentRemoteRWS
                   Gauge32,
               l2tpTunnelStatsTxSeq
                   Integer32,
               l2tpTunnelStatsTxSeqAck
                   Integer32,
               l2tpTunnelStatsRxSeq
                   Integer32,
               l2tpTunnelStatsRxSeqAck
                   Integer32,
               l2tpTunnelStatsTotalSessions
                   Counter32,
               l2tpTunnelStatsFailedSessions
                   Counter32,
               l2tpTunnelStatsActiveSessions
                   Gauge32,
               l2tpTunnelStatsLastResultCode
                   Integer32,
               l2tpTunnelStatsLastErrorCode
                   Integer32,
               l2tpTunnelStatsLastErrorMessage
                   SnmpAdminString,
               l2tpTunnelStatsDrainingTunnel
                   TruthValue
           }

   l2tpTunnelStatsLocalTID OBJECT-TYPE
           SYNTAX          Integer32 (0..65535)





           MAX-ACCESS      read-only
           STATUS          current
           ::= { l2tpTunnelStatsEntry 1 }

   l2tpTunnelStatsRemoteTID OBJECT-TYPE
           SYNTAX          Integer32 (0..65535)
           MAX-ACCESS      read-only
           STATUS          current
           ::= { l2tpTunnelStatsEntry 2 }

   l2tpTunnelStatsState    OBJECT-TYPE
           SYNTAX          INTEGER {
                               tunnelIdle(1),
                               tunnelConnecting(2),
                               tunnelEstablished(3),
                               tunnelDisconnecting(4)
                           }
           MAX-ACCESS      read-only
           STATUS          current
           ::= { l2tpTunnelStatsEntry 3 }

   l2tpTunnelStatsInitiated OBJECT-TYPE
           SYNTAX          INTEGER {
                               locally(1),
                               remotely(2)
                           }
           MAX-ACCESS      read-only
           STATUS          current
           ::= { l2tpTunnelStatsEntry 4 }

   l2tpTunnelStatsRemoteHostName OBJECT-TYPE
           SYNTAX          SnmpAdminString
           MAX-ACCESS      read-only
           STATUS          current
           ::= { l2tpTunnelStatsEntry 5 }

   l2tpTunnelStatsRemoteVendorName OBJECT-TYPE
           SYNTAX          SnmpAdminString
           MAX-ACCESS      read-only
           STATUS          current
           ::= { l2tpTunnelStatsEntry 6 }

   l2tpTunnelStatsRemoteFirmwareRev OBJECT-TYPE
           SYNTAX          Integer32
           MAX-ACCESS      read-only
           STATUS          current
           ::= { l2tpTunnelStatsEntry 7 }

   l2tpTunnelStatsRemoteProtocolVer OBJECT-TYPE
           SYNTAX          OCTET STRING (SIZE(2))
           MAX-ACCESS      read-only
           STATUS          current
           ::= { l2tpTunnelStatsEntry 8 }

   l2tpTunnelStatsInitialRemoteRWS OBJECT-TYPE
           SYNTAX          Integer32 (0..65535)
           MAX-ACCESS      read-only
           STATUS          current
           ::= { l2tpTunnelStatsEntry 9 }

   l2tpTunnelStatsBearerCaps OBJECT-TYPE
           SYNTAX          INTEGER {
                               none(1),
                               digital(2),
                               analog(3),
                               digitalAnalog(4)
                           }
           MAX-ACCESS      read-only
           STATUS          current
           ::= { l2tpTunnelStatsEntry 10 }

   l2tpTunnelStatsFramingCaps OBJECT-TYPE
           SYNTAX          INTEGER {
                               none(1),
                               sync(2),
                               async(3),
                               syncAsync(4)
                           }
           MAX-ACCESS      read-only
           STATUS          current
           ::= { l2tpTunnelStatsEntry 11 }

   l2tpTunnelStatsControlRxPkts OBJECT-TYPE
           SYNTAX          Counter32
           MAX-ACCESS      read-only
           STATUS          current
           ::= { l2tpTunnelStatsEntry 12 }

   l2tpTunnelStatsControlRxZLB OBJECT-TYPE
           SYNTAX          Counter32
           MAX-ACCESS      read-only





           STATUS          current
           ::= { l2tpTunnelStatsEntry 13 }

   l2tpTunnelStatsControlOutOfSeq OBJECT-TYPE
           SYNTAX          Counter32
           MAX-ACCESS      read-only
           STATUS          current
           ::= { l2tpTunnelStatsEntry 14 }

   l2tpTunnelStatsControlOutOfWin OBJECT-TYPE
           SYNTAX          Counter32
           MAX-ACCESS      read-only
           STATUS          current
           ::= { l2tpTunnelStatsEntry 15 }

   l2tpTunnelStatsControlTxPkts OBJECT-TYPE
           SYNTAX          Counter32
           MAX-ACCESS      read-only
           STATUS          current
           ::= { l2tpTunnelStatsEntry 16 }

   l2tpTunnelStatsControlTxZLB OBJECT-TYPE
           SYNTAX          Counter32
           MAX-ACCESS      read-only
           STATUS          current
           ::= { l2tpTunnelStatsEntry 17 }

   l2tpTunnelStatsControlAckTO OBJECT-TYPE
           SYNTAX          Counter32
           MAX-ACCESS      read-only
           STATUS          current
           ::= { l2tpTunnelStatsEntry 18 }

   l2tpTunnelStatsCurrentRemoteRWS OBJECT-TYPE
           SYNTAX          Gauge32 (0..65535)
           MAX-ACCESS      read-only
           STATUS          current
           ::= { l2tpTunnelStatsEntry 19 }

   l2tpTunnelStatsTxSeq  OBJECT-TYPE
           SYNTAX          Integer32 (0..65535)
           MAX-ACCESS      read-only
           STATUS          current
           ::= { l2tpTunnelStatsEntry 20 }

   l2tpTunnelStatsTxSeqAck OBJECT-TYPE
           SYNTAX          Integer32 (0..65535)
           MAX-ACCESS      read-only
           STATUS          current
           ::= { l2tpTunnelStatsEntry 21 }

   l2tpTunnelStatsRxSeq  OBJECT-TYPE
           SYNTAX          Integer32 (0..65535)





           MAX-ACCESS      read-only
           STATUS          current
           ::= { l2tpTunnelStatsEntry 22 }

   l2tpTunnelStatsRxSeqAck OBJECT-TYPE
           SYNTAX          Integer32 (0..65535)
           MAX-ACCESS      read-only
           STATUS          current
           ::= { l2tpTunnelStatsEntry 23 }

   l2tpTunnelStatsTotalSessions OBJECT-TYPE
           SYNTAX          Counter32
           MAX-ACCESS      read-only
           STATUS          current
           ::= { l2tpTunnelStatsEntry 24 }

   l2tpTunnelStatsFailedSessions OBJECT-TYPE
           SYNTAX          Counter32
           MAX-ACCESS      read-only
           STATUS          current
           ::= { l2tpTunnelStatsEntry 25 }

   l2tpTunnelStatsActiveSessions OBJECT-TYPE
           SYNTAX          Gauge32
           MAX-ACCESS      read-only
           STATUS          current
           ::= { l2tpTunnelStatsEntry 26 }

   l2tpTunnelStatsLastResultCode OBJECT-TYPE





           SYNTAX          Integer32 (0..65535)
           MAX-ACCESS      read-only
           STATUS          current
           ::= { l2tpTunnelStatsEntry 27 }

   l2tpTunnelStatsLastErrorCode OBJECT-TYPE
           SYNTAX          Integer32 (0..65535)
           MAX-ACCESS      read-only
           STATUS          current
           ::= { l2tpTunnelStatsEntry 28 }

   l2tpTunnelStatsLastErrorMessage OBJECT-TYPE
           SYNTAX          SnmpAdminString
           MAX-ACCESS      read-only
           STATUS          current
           ::= { l2tpTunnelStatsEntry 29 }

   l2tpTunnelStatsDrainingTunnel OBJECT-TYPE
           SYNTAX          TruthValue
           MAX-ACCESS      read-only
           STATUS          current
           ::= { l2tpTunnelStatsEntry 30 }







   l2tpSessionStatsTable   OBJECT-TYPE
           SYNTAX          SEQUENCE OF L2tpSessionStatsEntry
           MAX-ACCESS      not-accessible
           STATUS          current
           ::= { l2tpObjects 7 }

   l2tpSessionStatsEntry   OBJECT-TYPE
           SYNTAX          L2tpSessionStatsEntry
           MAX-ACCESS      not-accessible
           STATUS          current
           INDEX { l2tpSessionStatsTunnelIfIndex,
                   l2tpSessionStatsLocalSID }
           ::= { l2tpSessionStatsTable 1 }

   L2tpSessionStatsEntry ::=
           SEQUENCE {
               l2tpSessionStatsTunnelIfIndex
                   InterfaceIndex,
               l2tpSessionStatsIfIndex
                   InterfaceIndex,
               l2tpSessionStatsLocalSID
                   Integer32,
               l2tpSessionStatsRemoteSID
                   Integer32,
               l2tpSessionStatsUserName
                   SnmpAdminString,
               l2tpSessionStatsState
                   INTEGER,
               l2tpSessionStatsCallType
                   INTEGER,
               l2tpSessionStatsCallSerialNumber
                   Unsigned32,
               l2tpSessionStatsTxConnectSpeed
                   Unsigned32,
               l2tpSessionStatsRxConnectSpeed
                   Unsigned32,
               l2tpSessionStatsCallBearerType
                   INTEGER,
               l2tpSessionStatsFramingType
                   INTEGER,
               l2tpSessionStatsPhysChanId





                   Unsigned32,
               l2tpSessionStatsDNIS
                   SnmpAdminString,
               l2tpSessionStatsCLID
                   SnmpAdminString,
               l2tpSessionStatsSubAddress
                   SnmpAdminString,
               l2tpSessionStatsPrivateGroupID
                   SnmpAdminString,
               l2tpSessionStatsProxyLcp
                   TruthValue,
               l2tpSessionStatsAuthMethod
                   INTEGER,
               l2tpSessionStatsSequencingState
                   INTEGER,
               l2tpSessionStatsOutSequence
                   Counter32,
               l2tpSessionStatsReassemblyTO
                   Counter32,
               l2tpSessionStatsTxSeq
                   Integer32,
               l2tpSessionStatsRxSeq
                   Integer32
           }

   l2tpSessionStatsTunnelIfIndex OBJECT-TYPE
           SYNTAX          InterfaceIndex
           MAX-ACCESS      not-accessible
           STATUS          current
           ::= { l2tpSessionStatsEntry 1 }

   l2tpSessionStatsIfIndex OBJECT-TYPE
           SYNTAX          InterfaceIndex
           MAX-ACCESS      read-only
           STATUS          current
           ::= { l2tpSessionStatsEntry 2 }

   l2tpSessionStatsLocalSID OBJECT-TYPE
           SYNTAX          Integer32 (1..65535)
           MAX-ACCESS      not-accessible





           STATUS          current
           ::= { l2tpSessionStatsEntry 3 }

   l2tpSessionStatsRemoteSID OBJECT-TYPE
           SYNTAX          Integer32  (0..65535)
           MAX-ACCESS      read-only
           STATUS          current
           ::= { l2tpSessionStatsEntry 4 }

   l2tpSessionStatsUserName OBJECT-TYPE
           SYNTAX          SnmpAdminString
           MAX-ACCESS      read-only
           STATUS          current
           ::= { l2tpSessionStatsEntry 5 }

   l2tpSessionStatsState   OBJECT-TYPE
           SYNTAX          INTEGER {
                               sessionIdle(1),
                               sessionConnecting(2),
                               sessionEstablished(3),
                               sessionDisconnecting(4)
                           }
           MAX-ACCESS      read-only
           STATUS          current
           ::= { l2tpSessionStatsEntry 6 }

   l2tpSessionStatsCallType OBJECT-TYPE
           SYNTAX          INTEGER {
                               lacIncoming(1),





                               lnsIncoming(2),
                               lacOutgoing(3),
                               lnsOutgoing(4)
                           }
           MAX-ACCESS      read-only
           STATUS          current
           ::= { l2tpSessionStatsEntry 7 }

   l2tpSessionStatsCallSerialNumber OBJECT-TYPE
           SYNTAX          Unsigned32
           MAX-ACCESS      read-only
           STATUS          current
           ::= { l2tpSessionStatsEntry 8 }

   l2tpSessionStatsTxConnectSpeed OBJECT-TYPE
           SYNTAX          Unsigned32
           UNITS           "bits per second"
           MAX-ACCESS      read-only
           STATUS          current
           ::= { l2tpSessionStatsEntry 9 }

   l2tpSessionStatsRxConnectSpeed OBJECT-TYPE
           SYNTAX          Unsigned32
           UNITS           "bits per second"
           MAX-ACCESS      read-only
           STATUS          current
           ::= { l2tpSessionStatsEntry 10 }

   l2tpSessionStatsCallBearerType OBJECT-TYPE
           SYNTAX          INTEGER {
                               none(1),





                               digital(2),
                               analog(3)
                           }
           MAX-ACCESS      read-only
           STATUS          current
           ::= { l2tpSessionStatsEntry 11 }

   l2tpSessionStatsFramingType OBJECT-TYPE
           SYNTAX          INTEGER {
                               none(1),
                               sync(2),
                               async(3)
                           }
           MAX-ACCESS      read-only
           STATUS          current
           ::= { l2tpSessionStatsEntry 12 }

   l2tpSessionStatsPhysChanId OBJECT-TYPE
           SYNTAX          Unsigned32
           MAX-ACCESS      read-only
           STATUS          current
           ::= { l2tpSessionStatsEntry 13 }

   l2tpSessionStatsDNIS    OBJECT-TYPE
           SYNTAX          SnmpAdminString
           MAX-ACCESS      read-only
           STATUS          current
           ::= { l2tpSessionStatsEntry 14 }

   l2tpSessionStatsCLID    OBJECT-TYPE
           SYNTAX          SnmpAdminString
           MAX-ACCESS      read-only
           STATUS          current
           ::= { l2tpSessionStatsEntry 15 }

   l2tpSessionStatsSubAddress OBJECT-TYPE
           SYNTAX          SnmpAdminString
           MAX-ACCESS      read-only
           STATUS          current
           ::= { l2tpSessionStatsEntry 16 }

   l2tpSessionStatsPrivateGroupID OBJECT-TYPE
           SYNTAX          SnmpAdminString
           MAX-ACCESS      read-only
           STATUS          current
           ::= { l2tpSessionStatsEntry 17 }

   l2tpSessionStatsProxyLcp OBJECT-TYPE
           SYNTAX          TruthValue
           MAX-ACCESS      read-only
           STATUS          current
           ::= { l2tpSessionStatsEntry 18 }

   l2tpSessionStatsAuthMethod OBJECT-TYPE
           SYNTAX          INTEGER {
                               none(1),
                               text(2),
                               pppChap(3),
                               pppPap(4),
                               pppEap(5),
                               pppMsChapV1(6),
                               pppMsChapV2(7),
                               other(8)
                           }





           MAX-ACCESS      read-only
           STATUS          current
           ::= { l2tpSessionStatsEntry 19 }

   l2tpSessionStatsSequencingState OBJECT-TYPE
           SYNTAX          INTEGER {
                               none(1),
                               remote(2),
                               local(3),
                               both(4)
                           }
           MAX-ACCESS      read-only
           STATUS          current
           ::= { l2tpSessionStatsEntry 20 }

   l2tpSessionStatsOutSequence OBJECT-TYPE
           SYNTAX          Counter32
           MAX-ACCESS      read-only
           STATUS          current
           ::= { l2tpSessionStatsEntry 21 }

   l2tpSessionStatsReassemblyTO OBJECT-TYPE
           SYNTAX          Counter32
           MAX-ACCESS      read-only
           STATUS          current
           ::= { l2tpSessionStatsEntry 22 }

   l2tpSessionStatsTxSeq OBJECT-TYPE
           SYNTAX          Integer32 (0..65535)
           MAX-ACCESS      read-only
           STATUS          current





           ::= { l2tpSessionStatsEntry 23 }

   l2tpSessionStatsRxSeq OBJECT-TYPE
           SYNTAX          Integer32 (0..65535)
           MAX-ACCESS      read-only
           STATUS          current
           ::= { l2tpSessionStatsEntry 24 }


   l2tpTunnelMapTable      OBJECT-TYPE
           SYNTAX          SEQUENCE OF L2tpTunnelMapEntry
           MAX-ACCESS      not-accessible
           STATUS          current
           ::= { l2tpObjects 8 }

   l2tpTunnelMapEntry OBJECT-TYPE
           SYNTAX          L2tpTunnelMapEntry
           MAX-ACCESS      not-accessible
           STATUS          current
           INDEX { l2tpTunnelMapLocalTID }
           ::= { l2tpTunnelMapTable 1 }

   L2tpTunnelMapEntry ::=
           SEQUENCE {
               l2tpTunnelMapLocalTID
                   Integer32,
               l2tpTunnelMapIfIndex
                   InterfaceIndex
           }

   l2tpTunnelMapLocalTID   OBJECT-TYPE
           SYNTAX          Integer32 (1..65535)





           MAX-ACCESS      not-accessible
           STATUS          current
           ::= { l2tpTunnelMapEntry 1 }

   l2tpTunnelMapIfIndex    OBJECT-TYPE
           SYNTAX          InterfaceIndex
           MAX-ACCESS      read-only
           STATUS          current
           ::= { l2tpTunnelMapEntry 2 }


   l2tpSessionMapTable     OBJECT-TYPE
           SYNTAX          SEQUENCE OF L2tpSessionMapEntry
           MAX-ACCESS      not-accessible
           STATUS          current
           ::= { l2tpObjects 9 }

   l2tpSessionMapEntry     OBJECT-TYPE
           SYNTAX          L2tpSessionMapEntry
           MAX-ACCESS      not-accessible
           STATUS          current
           INDEX { l2tpSessionMapIfIndex }
           ::= { l2tpSessionMapTable 1 }

   L2tpSessionMapEntry ::=
           SEQUENCE {
               l2tpSessionMapIfIndex
                   InterfaceIndex,
               l2tpSessionMapTunnelIfIndex
                   InterfaceIndex,
               l2tpSessionMapLocalSID





                   Integer32,
               l2tpSessionMapStatus
                   RowStatus
           }

   l2tpSessionMapIfIndex   OBJECT-TYPE
           SYNTAX          InterfaceIndex
           MAX-ACCESS      not-accessible
           STATUS          current
           ::= { l2tpSessionMapEntry 1 }

   l2tpSessionMapTunnelIfIndex OBJECT-TYPE
           SYNTAX          InterfaceIndex
           MAX-ACCESS      read-create
           STATUS          current
           ::= { l2tpSessionMapEntry 2 }

   l2tpSessionMapLocalSID  OBJECT-TYPE
           SYNTAX          Integer32 (1..65535)
           MAX-ACCESS      read-only
           STATUS          current
           ::= { l2tpSessionMapEntry 3 }

   l2tpSessionMapStatus    OBJECT-TYPE
           SYNTAX          RowStatus
           MAX-ACCESS      read-create
           STATUS          current
           ::= { l2tpSessionMapEntry 4 }







   l2tpUdpStatsTable       OBJECT-TYPE
           SYNTAX          SEQUENCE OF L2tpUdpStatsEntry
           MAX-ACCESS      not-accessible
           STATUS          current
           ::= { l2tpIpUdpObjects 2 }

   l2tpUdpStatsEntry       OBJECT-TYPE
           SYNTAX          L2tpUdpStatsEntry
           MAX-ACCESS      not-accessible
           STATUS          current
           INDEX { l2tpUdpStatsIfIndex }
           ::= { l2tpUdpStatsTable 1 }

   L2tpUdpStatsEntry ::=
           SEQUENCE {
               l2tpUdpStatsIfIndex
                   InterfaceIndex,
               l2tpUdpStatsPeerPort
                   Integer32,
               l2tpUdpStatsLocalPort
                   Integer32
           }

   l2tpUdpStatsIfIndex     OBJECT-TYPE
           SYNTAX          InterfaceIndex
           MAX-ACCESS      not-accessible
           STATUS          current
           ::= { l2tpUdpStatsEntry 1 }

   l2tpUdpStatsPeerPort    OBJECT-TYPE
           SYNTAX          Integer32 (0..65535)
           MAX-ACCESS      read-only





           STATUS          current
           ::= { l2tpUdpStatsEntry 2 }

   l2tpUdpStatsLocalPort   OBJECT-TYPE
           SYNTAX          Integer32 (0..65535)
           MAX-ACCESS      read-only
           STATUS          current
           ::= { l2tpUdpStatsEntry 3 }


   l2tpTunnelAuthFailure NOTIFICATION-TYPE
           OBJECTS         {
                           l2tpTunnelStatsInitiated,
                           l2tpTunnelStatsRemoteHostName
                           }
           STATUS          current
           ::= { l2tpNotifications 1 }


   l2tpGroups      OBJECT IDENTIFIER ::= { l2tpConformance 1 }
   l2tpCompliances OBJECT IDENTIFIER ::= { l2tpConformance 2 }


   l2tpMIBFullCompliance MODULE-COMPLIANCE
           STATUS          current

           MODULE          -- this module

           MANDATORY-GROUPS {
                               l2tpConfigGroup,
                               l2tpStatsGroup,
                               l2tpTrapGroup
                            }
           GROUP           l2tpIpUdpGroup

           GROUP           l2tpDomainGroup

           GROUP           l2tpMappingGroup

           GROUP           l2tpSecurityGroup

           GROUP           l2tpHCPacketGroup

          ::= { l2tpCompliances 1 }

   l2tpMIBReadOnlyCompliance MODULE-COMPLIANCE





           STATUS          current

           MODULE          -- this module

           MANDATORY-GROUPS {
                               l2tpConfigGroup,
                               l2tpStatsGroup,
                               l2tpTrapGroup
                            }

           OBJECT   l2tpAdminState
           MIN-ACCESS read-only

           OBJECT   l2tpDrainTunnels
           MIN-ACCESS read-only

           OBJECT   l2tpTunnelConfigDomainId
           MIN-ACCESS read-only

           OBJECT   l2tpTunnelConfigHelloInterval
           MIN-ACCESS read-only

           OBJECT   l2tpTunnelConfigIdleTimeout
           MIN-ACCESS read-only

           OBJECT   l2tpTunnelConfigControlRWS
           MIN-ACCESS read-only

           OBJECT   l2tpTunnelConfigControlMaxRetx





           MIN-ACCESS read-only

           OBJECT   l2tpTunnelConfigControlMaxRetxTO
           MIN-ACCESS read-only

           OBJECT   l2tpTunnelConfigPayloadSeq
           MIN-ACCESS read-only

           OBJECT   l2tpTunnelConfigReassemblyTO
           MIN-ACCESS read-only

           OBJECT   l2tpTunnelConfigTransport
           MIN-ACCESS read-only

           OBJECT   l2tpTunnelConfigDrainTunnel
           MIN-ACCESS read-only

           OBJECT   l2tpTunnelConfigProxyPPPAuth
           MIN-ACCESS read-only

           GROUP           l2tpIpUdpGroup

           GROUP           l2tpDomainGroup

           OBJECT   l2tpDomainConfigAdminState
           MIN-ACCESS read-only






           OBJECT   l2tpDomainConfigDrainTunnels
           MIN-ACCESS read-only

           OBJECT   l2tpDomainConfigTunnelHelloInt
           MIN-ACCESS read-only

           OBJECT   l2tpDomainConfigTunnelIdleTO
           MIN-ACCESS read-only

           OBJECT   l2tpDomainConfigControlRWS
           MIN-ACCESS read-only

           OBJECT   l2tpDomainConfigControlMaxRetx
           MIN-ACCESS read-only

           OBJECT   l2tpDomainConfigControlMaxRetxTO
           MIN-ACCESS read-only

           OBJECT   l2tpDomainConfigPayloadSeq
           MIN-ACCESS read-only

           OBJECT   l2tpDomainConfigReassemblyTO
           MIN-ACCESS read-only

           OBJECT   l2tpDomainConfigProxyPPPAuth
           MIN-ACCESS read-only






           OBJECT   l2tpDomainConfigStorageType
           MIN-ACCESS read-only

           OBJECT   l2tpDomainConfigStatus
           MIN-ACCESS read-only

           GROUP           l2tpMappingGroup

           OBJECT   l2tpSessionMapTunnelIfIndex
           MIN-ACCESS read-only

           OBJECT   l2tpSessionMapStatus
           MIN-ACCESS read-only

           GROUP           l2tpSecurityGroup

           OBJECT   l2tpDomainConfigAuth
           MIN-ACCESS read-only

           OBJECT   l2tpDomainConfigSecret
           MIN-ACCESS read-only

           OBJECT   l2tpDomainConfigTunnelSecurity
           MIN-ACCESS read-only






           OBJECT   l2tpTunnelConfigAuth
           MIN-ACCESS read-only

           OBJECT   l2tpTunnelConfigSecret
           MIN-ACCESS read-only

           OBJECT   l2tpTunnelConfigSecurity
           MIN-ACCESS read-only

           GROUP           l2tpHCPacketGroup

           ::= { l2tpCompliances 2 }


   l2tpConfigGroup OBJECT-GROUP
           OBJECTS {
               l2tpAdminState,
               l2tpDrainTunnels,
               l2tpTunnelConfigDomainId,
               l2tpTunnelConfigHelloInterval,
               l2tpTunnelConfigIdleTimeout,
               l2tpTunnelConfigControlRWS,
               l2tpTunnelConfigControlMaxRetx,
               l2tpTunnelConfigControlMaxRetxTO,
               l2tpTunnelConfigPayloadSeq,
               l2tpTunnelConfigReassemblyTO,
               l2tpTunnelConfigTransport,
               l2tpTunnelConfigDrainTunnel,
               l2tpTunnelConfigProxyPPPAuth
           }
           STATUS          current





           ::= { l2tpGroups 1 }

   l2tpStatsGroup OBJECT-GROUP
           OBJECTS {
               l2tpProtocolVersions,
               l2tpVendorName,
               l2tpFirmwareRev,
               l2tpDrainingTunnels,
               l2tpTunnelStatsLocalTID,
               l2tpTunnelStatsRemoteTID,
               l2tpTunnelStatsState,
               l2tpTunnelStatsInitiated,
               l2tpTunnelStatsRemoteHostName,
               l2tpTunnelStatsRemoteVendorName,
               l2tpTunnelStatsRemoteFirmwareRev,
               l2tpTunnelStatsRemoteProtocolVer,
               l2tpTunnelStatsInitialRemoteRWS,
               l2tpTunnelStatsBearerCaps,
               l2tpTunnelStatsFramingCaps,
               l2tpTunnelStatsControlRxPkts,
               l2tpTunnelStatsControlRxZLB,
               l2tpTunnelStatsControlOutOfSeq,
               l2tpTunnelStatsControlOutOfWin,
               l2tpTunnelStatsControlTxPkts,
               l2tpTunnelStatsControlTxZLB,
               l2tpTunnelStatsControlAckTO,
               l2tpTunnelStatsCurrentRemoteRWS,
               l2tpTunnelStatsTxSeq,
               l2tpTunnelStatsTxSeqAck,
               l2tpTunnelStatsRxSeq,
               l2tpTunnelStatsRxSeqAck,
               l2tpTunnelStatsTotalSessions,
               l2tpTunnelStatsFailedSessions,
               l2tpTunnelStatsActiveSessions,
               l2tpTunnelStatsLastResultCode,
               l2tpTunnelStatsLastErrorCode,
               l2tpTunnelStatsLastErrorMessage,
               l2tpTunnelStatsDrainingTunnel,
               l2tpSessionStatsIfIndex,
               l2tpSessionStatsRemoteSID,
               l2tpSessionStatsUserName,
               l2tpSessionStatsState,
               l2tpSessionStatsCallType,
               l2tpSessionStatsCallSerialNumber,
               l2tpSessionStatsTxConnectSpeed,
               l2tpSessionStatsRxConnectSpeed,
               l2tpSessionStatsCallBearerType,
               l2tpSessionStatsFramingType,





               l2tpSessionStatsPhysChanId,
               l2tpSessionStatsDNIS,
               l2tpSessionStatsCLID,
               l2tpSessionStatsSubAddress,
               l2tpSessionStatsPrivateGroupID,
               l2tpSessionStatsProxyLcp,
               l2tpSessionStatsAuthMethod,
               l2tpSessionStatsSequencingState,
               l2tpSessionStatsOutSequence,
               l2tpSessionStatsReassemblyTO,
               l2tpSessionStatsTxSeq,
               l2tpSessionStatsRxSeq
           }
           STATUS          current
           ::= { l2tpGroups 2 }

   l2tpIpUdpGroup OBJECT-GROUP
           OBJECTS {
               l2tpUdpStatsPeerPort,
               l2tpUdpStatsLocalPort
           }
           STATUS          current
           ::= { l2tpGroups 3 }

   l2tpDomainGroup OBJECT-GROUP
           OBJECTS {
               l2tpDomainConfigAdminState,
               l2tpDomainConfigDrainTunnels,
               l2tpDomainConfigTunnelHelloInt,
               l2tpDomainConfigTunnelIdleTO,
               l2tpDomainConfigControlRWS,
               l2tpDomainConfigControlMaxRetx,
               l2tpDomainConfigControlMaxRetxTO,
               l2tpDomainConfigPayloadSeq,
               l2tpDomainConfigReassemblyTO,
               l2tpDomainConfigProxyPPPAuth,
               l2tpDomainConfigStorageType,
               l2tpDomainConfigStatus,
               l2tpDomainStatsTotalTunnels,
               l2tpDomainStatsFailedTunnels,
               l2tpDomainStatsFailedAuths,





               l2tpDomainStatsActiveTunnels,
               l2tpDomainStatsTotalSessions,
               l2tpDomainStatsFailedSessions,
               l2tpDomainStatsActiveSessions,
               l2tpDomainStatsDrainingTunnels,
               l2tpDomainStatsControlRxOctets,
               l2tpDomainStatsControlRxPkts,
               l2tpDomainStatsControlTxOctets,
               l2tpDomainStatsControlTxPkts,
               l2tpDomainStatsPayloadRxOctets,
               l2tpDomainStatsPayloadRxPkts,
               l2tpDomainStatsPayloadRxDiscs,
               l2tpDomainStatsPayloadTxOctets,
               l2tpDomainStatsPayloadTxPkts
           }
           STATUS          current
           ::= { l2tpGroups 4 }

   l2tpMappingGroup OBJECT-GROUP
           OBJECTS {
               l2tpTunnelMapIfIndex,
               l2tpSessionMapTunnelIfIndex,
               l2tpSessionMapLocalSID,
               l2tpSessionMapStatus
           }
           STATUS          current
           ::= { l2tpGroups 5 }

   l2tpSecurityGroup OBJECT-GROUP
           OBJECTS {
               l2tpDomainConfigAuth,
               l2tpDomainConfigSecret,
               l2tpDomainConfigTunnelSecurity,
               l2tpTunnelConfigAuth,
               l2tpTunnelConfigSecret,
               l2tpTunnelConfigSecurity
           }
           STATUS          current
           ::= { l2tpGroups 6 }






   l2tpTrapGroup NOTIFICATION-GROUP
           NOTIFICATIONS {
               l2tpTunnelAuthFailure
           }
           STATUS          current
           ::= { l2tpGroups 7 }

   l2tpHCPacketGroup OBJECT-GROUP
           OBJECTS {
               l2tpDomainStatsControlHCRxOctets,
               l2tpDomainStatsControlHCRxPkts,
               l2tpDomainStatsControlHCTxOctets,
               l2tpDomainStatsControlHCTxPkts,
               l2tpDomainStatsPayloadHCRxOctets,
               l2tpDomainStatsPayloadHCRxPkts,
               l2tpDomainStatsPayloadHCRxDiscs,
               l2tpDomainStatsPayloadHCTxOctets,
               l2tpDomainStatsPayloadHCTxPkts
            }
           STATUS          current
           ::= { l2tpGroups 8 }

   END
