FIBRE-CHANNEL-FE-MIB DEFINITIONS ::= BEGIN
  IMPORTS
    MODULE-IDENTITY, OBJECT-TYPE,
    Unsigned32, Counter32, Gauge32, Integer32, mib-2
      FROM SNMPv2-SMI
    TEXTUAL-CONVENTION, TruthValue, TimeStamp
      FROM SNMPv2-TC
    SnmpAdminString
      FROM SNMP-FRAMEWORK-MIB                   -- rfc2571
    MODULE-COMPLIANCE, OBJECT-GROUP
      FROM SNMPv2-CONF;

  fcFeMIB MODULE-IDENTITY
    LAST-UPDATED "200005180000Z"
    ORGANIZATION "IETF IPFC Working Group"

    ::= { mib-2 75 }

  fcFeMIBObjects OBJECT IDENTIFIER ::= { fcFeMIB 1 }







  fcFeConfig       OBJECT IDENTIFIER ::= { fcFeMIBObjects 1 }
  fcFeStatus       OBJECT IDENTIFIER ::= { fcFeMIBObjects 2 }
  fcFeError        OBJECT IDENTIFIER ::= { fcFeMIBObjects 3 }
  fcFeAccounting   OBJECT IDENTIFIER ::= { fcFeMIBObjects 4 }
  fcFeCapabilities OBJECT IDENTIFIER ::= { fcFeMIBObjects 5 }

  MilliSeconds ::= TEXTUAL-CONVENTION
    STATUS         current
    SYNTAX         Unsigned32

  MicroSeconds ::= TEXTUAL-CONVENTION
    STATUS         current
    SYNTAX         Unsigned32

  FcNameId ::= TEXTUAL-CONVENTION
    STATUS         current
    SYNTAX         OCTET STRING (SIZE (8))

  FcAddressId ::= TEXTUAL-CONVENTION
    STATUS         current
    SYNTAX         OCTET STRING (SIZE (3))

  FcRxDataFieldSize ::= TEXTUAL-CONVENTION
    STATUS         current
    SYNTAX         Integer32 (128..2112)

  FcBbCredit ::= TEXTUAL-CONVENTION
    STATUS         current
    SYNTAX         Integer32 (0..32767)

  FcphVersion ::= TEXTUAL-CONVENTION
    STATUS         current
    SYNTAX         Integer32 (0..255)

  FcStackedConnMode ::= TEXTUAL-CONVENTION





    STATUS         current
    SYNTAX         INTEGER {
                        none(1),
                        transparent(2),
                        lockedDown(3)
    }

  FcCosCap ::= TEXTUAL-CONVENTION
    STATUS         current
    SYNTAX         BITS { classF(0), class1(1), class2(2), class3(3),
                          class4(4), class5(5), class6(6) }

  FcFeModuleCapacity ::= TEXTUAL-CONVENTION
    STATUS         current
    SYNTAX         Unsigned32

  FcFeFxPortCapacity ::= TEXTUAL-CONVENTION
    STATUS         current
    SYNTAX         Unsigned32

  FcFeModuleIndex ::= TEXTUAL-CONVENTION
    STATUS         current
    SYNTAX         Unsigned32

  FcFeFxPortIndex ::= TEXTUAL-CONVENTION
    STATUS         current
    SYNTAX         Unsigned32

  FcFeNxPortIndex ::= TEXTUAL-CONVENTION
    STATUS         current
    SYNTAX         Integer32 (1..126)

  FcBbCreditModel ::= TEXTUAL-CONVENTION
    STATUS         current
    SYNTAX         INTEGER { regular(1), alternate (2) }







  fcFeFabricName OBJECT-TYPE
      SYNTAX      FcNameId
      MAX-ACCESS  read-write
      STATUS      current
  ::= { fcFeConfig 1 }

  fcFeElementName OBJECT-TYPE
      SYNTAX      FcNameId
      MAX-ACCESS  read-write
      STATUS      current
  ::= { fcFeConfig 2 }

  fcFeModuleCapacity OBJECT-TYPE
      SYNTAX      FcFeModuleCapacity
      MAX-ACCESS  read-only
      STATUS      current
  ::= { fcFeConfig 3 }


  fcFeModuleTable OBJECT-TYPE
      SYNTAX      SEQUENCE OF FcFeModuleEntry
      MAX-ACCESS  not-accessible
      STATUS      current
  ::= { fcFeConfig 4 }

  fcFeModuleEntry OBJECT-TYPE





      SYNTAX      FcFeModuleEntry
      MAX-ACCESS  not-accessible
      STATUS      current
      INDEX { fcFeModuleIndex }
  ::= { fcFeModuleTable 1 }


  FcFeModuleEntry ::=
      SEQUENCE {
          fcFeModuleIndex
              FcFeModuleIndex,
          fcFeModuleDescr
              SnmpAdminString,
          fcFeModuleObjectID
              OBJECT IDENTIFIER,
          fcFeModuleOperStatus
              INTEGER,
          fcFeModuleLastChange
              TimeStamp,
          fcFeModuleFxPortCapacity
              FcFeFxPortCapacity,
          fcFeModuleName
              FcNameId
      }

  fcFeModuleIndex OBJECT-TYPE
      SYNTAX      FcFeModuleIndex
      MAX-ACCESS  not-accessible
      STATUS      current
  ::= { fcFeModuleEntry 1 }

  fcFeModuleDescr OBJECT-TYPE
      SYNTAX      SnmpAdminString
      MAX-ACCESS  read-only
      STATUS      current
  ::= { fcFeModuleEntry 2 }






  fcFeModuleObjectID OBJECT-TYPE
      SYNTAX      OBJECT IDENTIFIER
      MAX-ACCESS  read-only
      STATUS      current
  ::= { fcFeModuleEntry 3 }

  fcFeModuleOperStatus    OBJECT-TYPE
      SYNTAX      INTEGER {
                      online  (1), -- functional
                      offline (2), -- not available
                      testing (3), -- under testing
                      faulty  (4)  -- defective
                  }
      MAX-ACCESS  read-only
      STATUS      current
  ::= { fcFeModuleEntry 4 }

  fcFeModuleLastChange OBJECT-TYPE
      SYNTAX      TimeStamp
      MAX-ACCESS  read-only
      STATUS      current
  ::= { fcFeModuleEntry 5 }

  fcFeModuleFxPortCapacity OBJECT-TYPE
      SYNTAX      FcFeFxPortCapacity





      MAX-ACCESS  read-only
      STATUS      current
  ::= { fcFeModuleEntry 6 }

  fcFeModuleName OBJECT-TYPE
      SYNTAX      FcNameId
      MAX-ACCESS  read-write
      STATUS      current
  ::= { fcFeModuleEntry 7 }


 fcFxPortTable OBJECT-TYPE
     SYNTAX      SEQUENCE OF FcFxPortEntry
     MAX-ACCESS  not-accessible
     STATUS      current
 ::= { fcFeConfig 5 }

 fcFxPortEntry OBJECT-TYPE
     SYNTAX      FcFxPortEntry
     MAX-ACCESS  not-accessible
     STATUS      current
     INDEX { fcFeModuleIndex, fcFxPortIndex }
 ::= { fcFxPortTable 1 }


 FcFxPortEntry ::=
     SEQUENCE {
         fcFxPortIndex
             FcFeFxPortIndex,
         fcFxPortName
             FcNameId,





         fcFxPortFcphVersionHigh
             FcphVersion,
         fcFxPortFcphVersionLow
             FcphVersion,
         fcFxPortBbCredit
             FcBbCredit,
         fcFxPortRxBufSize
             FcRxDataFieldSize,
         fcFxPortRatov
             MilliSeconds,
         fcFxPortEdtov
             MilliSeconds,
         fcFxPortCosSupported
             FcCosCap,
         fcFxPortIntermixSupported
             TruthValue,
         fcFxPortStackedConnMode
             FcStackedConnMode,
         fcFxPortClass2SeqDeliv
             TruthValue,
         fcFxPortClass3SeqDeliv
             TruthValue,
         fcFxPortHoldTime
             MicroSeconds
     }

  fcFxPortIndex OBJECT-TYPE
      SYNTAX      FcFeFxPortIndex
      MAX-ACCESS  not-accessible
      STATUS      current
  ::= { fcFxPortEntry 1 }

  fcFxPortName OBJECT-TYPE
      SYNTAX      FcNameId
      MAX-ACCESS  read-only
      STATUS      current
  ::= { fcFxPortEntry 2 }






  fcFxPortFcphVersionHigh OBJECT-TYPE
      SYNTAX      FcphVersion
      MAX-ACCESS  read-only
      STATUS      current
  ::= { fcFxPortEntry 3 }

  fcFxPortFcphVersionLow OBJECT-TYPE
      SYNTAX      FcphVersion
      MAX-ACCESS  read-only
      STATUS      current
  ::= { fcFxPortEntry 4 }

  fcFxPortBbCredit OBJECT-TYPE
      SYNTAX      FcBbCredit
      UNITS       "buffers"
      MAX-ACCESS  read-only
      STATUS      current
      ::= { fcFxPortEntry 5 }

  fcFxPortRxBufSize OBJECT-TYPE
      SYNTAX      FcRxDataFieldSize
      UNITS       "bytes"
      MAX-ACCESS  read-only
      STATUS      current
  ::= { fcFxPortEntry 6 }

  fcFxPortRatov OBJECT-TYPE
      SYNTAX      MilliSeconds
      UNITS       "milliseconds"
      MAX-ACCESS  read-only
      STATUS      current





      ::= { fcFxPortEntry 7 }

  fcFxPortEdtov OBJECT-TYPE
      SYNTAX      MilliSeconds
      UNITS       "milliseconds"
      MAX-ACCESS  read-only
      STATUS      current
  ::= { fcFxPortEntry 8 }



  fcFxPortCosSupported OBJECT-TYPE
      SYNTAX      FcCosCap
      MAX-ACCESS  read-only
      STATUS      current
  ::= { fcFxPortEntry 9 }

  fcFxPortIntermixSupported OBJECT-TYPE
      SYNTAX      TruthValue
      MAX-ACCESS  read-only
      STATUS      current
  ::= { fcFxPortEntry 10 }

  fcFxPortStackedConnMode OBJECT-TYPE
      SYNTAX      FcStackedConnMode
      MAX-ACCESS  read-only
      STATUS      current





  ::= { fcFxPortEntry 11 }

  fcFxPortClass2SeqDeliv OBJECT-TYPE
      SYNTAX      TruthValue
      MAX-ACCESS  read-only
      STATUS      current
  ::= { fcFxPortEntry 12 }

  fcFxPortClass3SeqDeliv OBJECT-TYPE
      SYNTAX      TruthValue
      MAX-ACCESS  read-only
      STATUS      current
  ::= { fcFxPortEntry 13 }



  fcFxPortHoldTime OBJECT-TYPE
      SYNTAX      MicroSeconds
      UNITS       "microseconds"
      MAX-ACCESS  read-only
      STATUS      current
  ::= { fcFxPortEntry 14 }





  fcFxPortStatusTable OBJECT-TYPE
      SYNTAX      SEQUENCE OF FcFxPortStatusEntry





      MAX-ACCESS  not-accessible
      STATUS      current
  ::= { fcFeStatus 1 }

  fcFxPortStatusEntry OBJECT-TYPE
      SYNTAX      FcFxPortStatusEntry
      MAX-ACCESS  not-accessible
      STATUS      current
      AUGMENTS { fcFxPortEntry }
  ::= { fcFxPortStatusTable 1 }


  FcFxPortStatusEntry ::=
      SEQUENCE {
          fcFxPortID
              FcAddressId,
          fcFxPortBbCreditAvailable
              Gauge32,
          fcFxPortOperMode
              INTEGER,
          fcFxPortAdminMode
              INTEGER
      }

  fcFxPortID   OBJECT-TYPE
      SYNTAX      FcAddressId
      MAX-ACCESS  read-only
      STATUS      current
  ::= { fcFxPortStatusEntry 1 }

  fcFxPortBbCreditAvailable OBJECT-TYPE
      SYNTAX      Gauge32
      UNITS       "buffers"
      MAX-ACCESS  read-only
      STATUS      current
  ::= { fcFxPortStatusEntry 2 }

  fcFxPortOperMode    OBJECT-TYPE
      SYNTAX              INTEGER { unknown(1), fPort(2), flPort(3) }
      MAX-ACCESS          read-only
      STATUS              current
  ::= { fcFxPortStatusEntry 3 }

  fcFxPortAdminMode   OBJECT-TYPE
      SYNTAX              INTEGER { fPort(2), flPort(3) }
      MAX-ACCESS          read-write
      STATUS              current
  ::= { fcFxPortStatusEntry 4 }



  fcFxPortPhysTable OBJECT-TYPE
      SYNTAX      SEQUENCE OF FcFxPortPhysEntry
      MAX-ACCESS  not-accessible
      STATUS      current
  ::= { fcFeStatus 2 }

  fcFxPortPhysEntry OBJECT-TYPE
      SYNTAX      FcFxPortPhysEntry
      MAX-ACCESS  not-accessible
      STATUS      current
      AUGMENTS { fcFxPortEntry }
  ::= { fcFxPortPhysTable 1 }

  FcFxPortPhysEntry ::=





      SEQUENCE {
          fcFxPortPhysAdminStatus
              INTEGER,
          fcFxPortPhysOperStatus
              INTEGER,
          fcFxPortPhysLastChange
              TimeStamp,
          fcFxPortPhysRttov
              MilliSeconds
      }

  fcFxPortPhysAdminStatus OBJECT-TYPE
      SYNTAX      INTEGER {
                      online  (1),  -- place port online
                      offline (2),  -- take port offline
                      testing (3)   -- initiate test procedures
                  }
      MAX-ACCESS  read-write
      STATUS      current
  ::= { fcFxPortPhysEntry 1 }

  fcFxPortPhysOperStatus   OBJECT-TYPE
      SYNTAX      INTEGER {
          online       (1), -- Login may proceed
          offline      (2), -- Login cannot proceed
          testing      (3), -- port is under test
          linkFailure  (4)  -- failure after online/testing
      }
      MAX-ACCESS  read-only
      STATUS      current
  ::= { fcFxPortPhysEntry 2 }

  fcFxPortPhysLastChange OBJECT-TYPE
      SYNTAX      TimeStamp
      MAX-ACCESS  read-only
      STATUS      current
  ::= { fcFxPortPhysEntry 3 }

  fcFxPortPhysRttov OBJECT-TYPE
      SYNTAX      MilliSeconds
      UNITS       "milliseconds"
      MAX-ACCESS  read-write
      STATUS      current
  ::= { fcFxPortPhysEntry 4 }


  fcFxLoginTable OBJECT-TYPE
      SYNTAX      SEQUENCE OF FcFxLoginEntry
      MAX-ACCESS  not-accessible
      STATUS      current
  ::= { fcFeStatus 3 }







  fcFxLoginEntry OBJECT-TYPE
      SYNTAX      FcFxLoginEntry
      MAX-ACCESS  not-accessible
      STATUS      current
      INDEX { fcFeModuleIndex, fcFxPortIndex, fcFxPortNxLoginIndex }
  ::= { fcFxLoginTable 1 }

  FcFxLoginEntry ::=
      SEQUENCE {
          fcFxPortNxLoginIndex
              FcFeNxPortIndex,
          fcFxPortFcphVersionAgreed
              FcphVersion,
          fcFxPortNxPortBbCredit
              FcBbCredit,
          fcFxPortNxPortRxDataFieldSize
              FcRxDataFieldSize,
          fcFxPortCosSuppAgreed
              FcCosCap,
          fcFxPortIntermixSuppAgreed
              TruthValue,
          fcFxPortStackedConnModeAgreed
              FcStackedConnMode,
          fcFxPortClass2SeqDelivAgreed
              TruthValue,
          fcFxPortClass3SeqDelivAgreed
              TruthValue,
          fcFxPortNxPortName
              FcNameId,
          fcFxPortConnectedNxPort
              FcAddressId,
          fcFxPortBbCreditModel
              FcBbCreditModel
      }

  fcFxPortNxLoginIndex OBJECT-TYPE
      SYNTAX      FcFeNxPortIndex
      MAX-ACCESS  not-accessible
      STATUS      current
  ::= { fcFxLoginEntry 1 }






  fcFxPortFcphVersionAgreed OBJECT-TYPE
      SYNTAX      FcphVersion
      MAX-ACCESS  read-only
      STATUS      current
  ::= { fcFxLoginEntry 2 }

  fcFxPortNxPortBbCredit OBJECT-TYPE
      SYNTAX      FcBbCredit
      UNITS       "buffers"
      MAX-ACCESS  read-only
      STATUS      current
  ::= { fcFxLoginEntry 3 }

  fcFxPortNxPortRxDataFieldSize OBJECT-TYPE
      SYNTAX      FcRxDataFieldSize
      UNITS       "bytes"
      MAX-ACCESS  read-only
      STATUS      current
  ::= { fcFxLoginEntry 4 }

  fcFxPortCosSuppAgreed OBJECT-TYPE
      SYNTAX      FcCosCap
      MAX-ACCESS  read-only
      STATUS      current
  ::= { fcFxLoginEntry 5 }

  fcFxPortIntermixSuppAgreed OBJECT-TYPE
      SYNTAX      TruthValue
      MAX-ACCESS  read-only
      STATUS      current





  ::= { fcFxLoginEntry 6 }

  fcFxPortStackedConnModeAgreed OBJECT-TYPE
      SYNTAX      FcStackedConnMode
      MAX-ACCESS  read-only
      STATUS      current
  ::= { fcFxLoginEntry 7 }

  fcFxPortClass2SeqDelivAgreed OBJECT-TYPE
      SYNTAX      TruthValue
      MAX-ACCESS  read-only
      STATUS      current
  ::= { fcFxLoginEntry 8 }

  fcFxPortClass3SeqDelivAgreed OBJECT-TYPE
      SYNTAX      TruthValue
      MAX-ACCESS  read-only
      STATUS      current
  ::= { fcFxLoginEntry 9 }

  fcFxPortNxPortName OBJECT-TYPE
      SYNTAX      FcNameId
      MAX-ACCESS  read-only
      STATUS      current
  ::= { fcFxLoginEntry 10 }

  fcFxPortConnectedNxPort OBJECT-TYPE
      SYNTAX      FcAddressId





      MAX-ACCESS  read-only
      STATUS      current
  ::= { fcFxLoginEntry 11 }

  fcFxPortBbCreditModel OBJECT-TYPE
      SYNTAX      FcBbCreditModel
      MAX-ACCESS  read-write
      STATUS      current
  ::= { fcFxLoginEntry 12 }




  fcFxPortErrorTable OBJECT-TYPE
      SYNTAX      SEQUENCE OF FcFxPortErrorEntry
      MAX-ACCESS  not-accessible
      STATUS      current
  ::= { fcFeError 1 }

  fcFxPortErrorEntry OBJECT-TYPE
      SYNTAX      FcFxPortErrorEntry
      MAX-ACCESS  not-accessible
      STATUS      current
      AUGMENTS { fcFxPortEntry }





  ::= { fcFxPortErrorTable 1 }


  FcFxPortErrorEntry ::=
      SEQUENCE {
          fcFxPortLinkFailures
              Counter32,
          fcFxPortSyncLosses
              Counter32,
          fcFxPortSigLosses
              Counter32,
          fcFxPortPrimSeqProtoErrors
              Counter32,
          fcFxPortInvalidTxWords
              Counter32,
          fcFxPortInvalidCrcs
              Counter32,
          fcFxPortDelimiterErrors
              Counter32,
          fcFxPortAddressIdErrors
              Counter32,
          fcFxPortLinkResetIns
              Counter32,
          fcFxPortLinkResetOuts
              Counter32,
          fcFxPortOlsIns
              Counter32,
          fcFxPortOlsOuts
              Counter32
      }

  fcFxPortLinkFailures OBJECT-TYPE
      SYNTAX      Counter32
      MAX-ACCESS  read-only
      STATUS      current
  ::= { fcFxPortErrorEntry 1 }

  fcFxPortSyncLosses OBJECT-TYPE
      SYNTAX      Counter32
      MAX-ACCESS  read-only
      STATUS      current
  ::= { fcFxPortErrorEntry 2 }






  fcFxPortSigLosses OBJECT-TYPE
      SYNTAX      Counter32
      MAX-ACCESS  read-only
      STATUS      current
  ::= { fcFxPortErrorEntry 3 }

  fcFxPortPrimSeqProtoErrors OBJECT-TYPE
      SYNTAX      Counter32
      MAX-ACCESS  read-only
      STATUS      current
  ::= { fcFxPortErrorEntry 4 }

  fcFxPortInvalidTxWords OBJECT-TYPE
      SYNTAX      Counter32
      MAX-ACCESS  read-only
      STATUS      current
  ::= { fcFxPortErrorEntry 5 }

  fcFxPortInvalidCrcs OBJECT-TYPE
      SYNTAX      Counter32
      MAX-ACCESS  read-only
      STATUS      current
  ::= { fcFxPortErrorEntry 6 }

  fcFxPortDelimiterErrors OBJECT-TYPE
      SYNTAX      Counter32
      MAX-ACCESS  read-only
      STATUS      current
  ::= { fcFxPortErrorEntry 7 }

  fcFxPortAddressIdErrors OBJECT-TYPE
      SYNTAX      Counter32
      MAX-ACCESS  read-only
      STATUS      current
  ::= { fcFxPortErrorEntry 8 }

  fcFxPortLinkResetIns OBJECT-TYPE
      SYNTAX      Counter32
      MAX-ACCESS  read-only
      STATUS      current
  ::= { fcFxPortErrorEntry 9 }

  fcFxPortLinkResetOuts OBJECT-TYPE
      SYNTAX      Counter32
      MAX-ACCESS  read-only
      STATUS      current
  ::= { fcFxPortErrorEntry 10 }

  fcFxPortOlsIns OBJECT-TYPE
      SYNTAX      Counter32
      MAX-ACCESS  read-only
      STATUS      current
  ::= { fcFxPortErrorEntry 11 }

  fcFxPortOlsOuts OBJECT-TYPE
      SYNTAX      Counter32
      MAX-ACCESS  read-only
      STATUS      current
  ::= { fcFxPortErrorEntry 12 }










  fcFxPortC1AccountingTable OBJECT-TYPE
      SYNTAX      SEQUENCE OF FcFxPortC1AccountingEntry
      MAX-ACCESS  not-accessible
      STATUS      current
  ::= { fcFeAccounting 1 }

  fcFxPortC1AccountingEntry OBJECT-TYPE
      SYNTAX      FcFxPortC1AccountingEntry
      MAX-ACCESS  not-accessible
      STATUS      current
      AUGMENTS { fcFxPortEntry }
  ::= { fcFxPortC1AccountingTable 1 }


  FcFxPortC1AccountingEntry ::=
      SEQUENCE {
          fcFxPortC1InFrames
              Counter32,
          fcFxPortC1OutFrames
              Counter32,
          fcFxPortC1InOctets
              Counter32,
          fcFxPortC1OutOctets
              Counter32,
          fcFxPortC1Discards
              Counter32,
          fcFxPortC1FbsyFrames
              Counter32,
          fcFxPortC1FrjtFrames
              Counter32,
          fcFxPortC1InConnections
              Counter32,
          fcFxPortC1OutConnections
              Counter32,
          fcFxPortC1ConnTime
              MilliSeconds
      }






  fcFxPortC1InFrames OBJECT-TYPE
      SYNTAX      Counter32
      MAX-ACCESS  read-only
      STATUS      current
  ::= { fcFxPortC1AccountingEntry 1 }

  fcFxPortC1OutFrames OBJECT-TYPE
      SYNTAX      Counter32
      MAX-ACCESS  read-only
      STATUS      current
  ::= { fcFxPortC1AccountingEntry 2 }

  fcFxPortC1InOctets OBJECT-TYPE
      SYNTAX      Counter32
      MAX-ACCESS  read-only
      STATUS      current
  ::= { fcFxPortC1AccountingEntry 3 }

  fcFxPortC1OutOctets OBJECT-TYPE
      SYNTAX      Counter32
      MAX-ACCESS  read-only
      STATUS      current
  ::= { fcFxPortC1AccountingEntry 4 }

  fcFxPortC1Discards OBJECT-TYPE
      SYNTAX      Counter32
      MAX-ACCESS  read-only
      STATUS      current
  ::= { fcFxPortC1AccountingEntry 5 }

  fcFxPortC1FbsyFrames OBJECT-TYPE





      SYNTAX      Counter32
      MAX-ACCESS  read-only
      STATUS      current
  ::= { fcFxPortC1AccountingEntry 6 }

  fcFxPortC1FrjtFrames OBJECT-TYPE
      SYNTAX      Counter32
      MAX-ACCESS  read-only
      STATUS      current
  ::= { fcFxPortC1AccountingEntry 7 }

  fcFxPortC1InConnections OBJECT-TYPE
      SYNTAX      Counter32
      MAX-ACCESS  read-only
      STATUS      current
  ::= { fcFxPortC1AccountingEntry 8 }

  fcFxPortC1OutConnections OBJECT-TYPE
      SYNTAX      Counter32
      MAX-ACCESS  read-only
      STATUS      current
  ::= { fcFxPortC1AccountingEntry 9 }

  fcFxPortC1ConnTime OBJECT-TYPE
      SYNTAX      MilliSeconds
      UNITS       "milliseconds"
      MAX-ACCESS  read-only
      STATUS      current





  ::= { fcFxPortC1AccountingEntry 10 }




  fcFxPortC2AccountingTable OBJECT-TYPE
      SYNTAX      SEQUENCE OF FcFxPortC2AccountingEntry
      MAX-ACCESS  not-accessible
      STATUS      current
  ::= { fcFeAccounting 2 }

  fcFxPortC2AccountingEntry OBJECT-TYPE
      SYNTAX      FcFxPortC2AccountingEntry
      MAX-ACCESS  not-accessible
      STATUS      current
      AUGMENTS { fcFxPortEntry }
  ::= { fcFxPortC2AccountingTable 1 }

  FcFxPortC2AccountingEntry ::=
      SEQUENCE {
          fcFxPortC2InFrames
              Counter32,
          fcFxPortC2OutFrames
                 Counter32,
          fcFxPortC2InOctets
                 Counter32,
          fcFxPortC2OutOctets
                 Counter32,
          fcFxPortC2Discards
                 Counter32,
          fcFxPortC2FbsyFrames
                 Counter32,
          fcFxPortC2FrjtFrames
                 Counter32
      }

  fcFxPortC2InFrames OBJECT-TYPE





      SYNTAX      Counter32
      MAX-ACCESS  read-only
      STATUS      current
  ::= { fcFxPortC2AccountingEntry 1 }

  fcFxPortC2OutFrames OBJECT-TYPE
      SYNTAX      Counter32
      MAX-ACCESS  read-only
      STATUS      current
  ::= { fcFxPortC2AccountingEntry 2 }

  fcFxPortC2InOctets OBJECT-TYPE
      SYNTAX      Counter32
      MAX-ACCESS  read-only
      STATUS      current
  ::= { fcFxPortC2AccountingEntry 3 }

  fcFxPortC2OutOctets OBJECT-TYPE
      SYNTAX      Counter32
      MAX-ACCESS  read-only
      STATUS      current
  ::= { fcFxPortC2AccountingEntry 4 }

  fcFxPortC2Discards OBJECT-TYPE
      SYNTAX      Counter32
      MAX-ACCESS  read-only
      STATUS      current
  ::= { fcFxPortC2AccountingEntry 5 }

  fcFxPortC2FbsyFrames OBJECT-TYPE
      SYNTAX      Counter32
      MAX-ACCESS  read-only





      STATUS      current
  ::= { fcFxPortC2AccountingEntry 6 }

  fcFxPortC2FrjtFrames OBJECT-TYPE
      SYNTAX      Counter32
      MAX-ACCESS  read-only
      STATUS      current
  ::= { fcFxPortC2AccountingEntry 7 }


  fcFxPortC3AccountingTable OBJECT-TYPE
      SYNTAX      SEQUENCE OF FcFxPortC3AccountingEntry
      MAX-ACCESS  not-accessible
      STATUS      current
  ::= { fcFeAccounting 3 }

  fcFxPortC3AccountingEntry OBJECT-TYPE
      SYNTAX      FcFxPortC3AccountingEntry
      MAX-ACCESS  not-accessible
      STATUS      current
      AUGMENTS { fcFxPortEntry }
  ::= { fcFxPortC3AccountingTable 1 }


  FcFxPortC3AccountingEntry ::=
      SEQUENCE {
          fcFxPortC3InFrames
              Counter32,
          fcFxPortC3OutFrames
              Counter32,
          fcFxPortC3InOctets





              Counter32,
          fcFxPortC3OutOctets
              Counter32,
          fcFxPortC3Discards
              Counter32
      }

  fcFxPortC3InFrames OBJECT-TYPE
      SYNTAX      Counter32
      MAX-ACCESS  read-only
      STATUS      current
  ::= { fcFxPortC3AccountingEntry 1 }

  fcFxPortC3OutFrames OBJECT-TYPE
      SYNTAX      Counter32
      MAX-ACCESS  read-only
      STATUS      current
  ::= { fcFxPortC3AccountingEntry 2 }

  fcFxPortC3InOctets OBJECT-TYPE
      SYNTAX      Counter32
      MAX-ACCESS  read-only
      STATUS      current
  ::= { fcFxPortC3AccountingEntry 3 }

  fcFxPortC3OutOctets OBJECT-TYPE
      SYNTAX      Counter32
      MAX-ACCESS  read-only
      STATUS      current
  ::= { fcFxPortC3AccountingEntry 4 }

  fcFxPortC3Discards OBJECT-TYPE
      SYNTAX      Counter32
      MAX-ACCESS  read-only





      STATUS      current
  ::= { fcFxPortC3AccountingEntry 5 }



  fcFxPortCapTable OBJECT-TYPE
      SYNTAX      SEQUENCE OF FcFxPortCapEntry
      MAX-ACCESS  not-accessible
      STATUS      current
  ::= { fcFeCapabilities 1 }

  fcFxPortCapEntry OBJECT-TYPE
      SYNTAX      FcFxPortCapEntry
      MAX-ACCESS  not-accessible
      STATUS      current
      AUGMENTS { fcFxPortEntry }
  ::= { fcFxPortCapTable 1 }


  FcFxPortCapEntry ::=
      SEQUENCE {
          fcFxPortCapFcphVersionHigh
              FcphVersion,
          fcFxPortCapFcphVersionLow
              FcphVersion,
          fcFxPortCapBbCreditMax
              FcBbCredit,
          fcFxPortCapBbCreditMin
              FcBbCredit,
          fcFxPortCapRxDataFieldSizeMax
              FcRxDataFieldSize,
          fcFxPortCapRxDataFieldSizeMin
              FcRxDataFieldSize,
          fcFxPortCapCos
              FcCosCap,
          fcFxPortCapIntermix





              TruthValue,
          fcFxPortCapStackedConnMode
              FcStackedConnMode,
          fcFxPortCapClass2SeqDeliv
              TruthValue,
          fcFxPortCapClass3SeqDeliv
              TruthValue,
          fcFxPortCapHoldTimeMax
              MicroSeconds,
          fcFxPortCapHoldTimeMin
              MicroSeconds
      }

  fcFxPortCapFcphVersionHigh OBJECT-TYPE
      SYNTAX      FcphVersion
      MAX-ACCESS  read-only
      STATUS      current
  ::= { fcFxPortCapEntry 1 }

  fcFxPortCapFcphVersionLow OBJECT-TYPE
      SYNTAX      FcphVersion
      MAX-ACCESS  read-only
      STATUS      current
  ::= { fcFxPortCapEntry 2 }

  fcFxPortCapBbCreditMax OBJECT-TYPE
      SYNTAX      FcBbCredit
      UNITS       "buffers"
      MAX-ACCESS  read-only
      STATUS      current
  ::= { fcFxPortCapEntry 3 }

  fcFxPortCapBbCreditMin OBJECT-TYPE
      SYNTAX      FcBbCredit
      UNITS       "buffers"
      MAX-ACCESS  read-only
      STATUS      current
  ::= { fcFxPortCapEntry 4 }

  fcFxPortCapRxDataFieldSizeMax OBJECT-TYPE
      SYNTAX      FcRxDataFieldSize
      UNITS       "bytes"
      MAX-ACCESS  read-only
      STATUS      current
  ::= { fcFxPortCapEntry 5 }

  fcFxPortCapRxDataFieldSizeMin OBJECT-TYPE
      SYNTAX      FcRxDataFieldSize
      UNITS       "bytes"
      MAX-ACCESS  read-only
      STATUS      current
  ::= { fcFxPortCapEntry 6 }

  fcFxPortCapCos OBJECT-TYPE
      SYNTAX      FcCosCap
      MAX-ACCESS  read-only
      STATUS      current
  ::= { fcFxPortCapEntry 7 }

  fcFxPortCapIntermix OBJECT-TYPE
      SYNTAX      TruthValue
      MAX-ACCESS  read-only
      STATUS      current
  ::= { fcFxPortCapEntry 8 }

  fcFxPortCapStackedConnMode OBJECT-TYPE





      SYNTAX      FcStackedConnMode
      MAX-ACCESS  read-only
      STATUS      current
  ::= { fcFxPortCapEntry 9 }

  fcFxPortCapClass2SeqDeliv OBJECT-TYPE
      SYNTAX      TruthValue
      MAX-ACCESS  read-only
      STATUS      current
  ::= { fcFxPortCapEntry 10 }

  fcFxPortCapClass3SeqDeliv OBJECT-TYPE
      SYNTAX      TruthValue
      MAX-ACCESS  read-only
      STATUS      current
  ::= { fcFxPortCapEntry 11 }

  fcFxPortCapHoldTimeMax OBJECT-TYPE
      SYNTAX      MicroSeconds
      UNITS       "microseconds"
      MAX-ACCESS  read-only
      STATUS      current
  ::= { fcFxPortCapEntry 12 }

  fcFxPortCapHoldTimeMin OBJECT-TYPE
      SYNTAX      MicroSeconds
      UNITS       "microseconds"
      MAX-ACCESS  read-only
      STATUS      current
  ::= { fcFxPortCapEntry 13 }







  fcFeMIBConformance OBJECT IDENTIFIER  ::= { fcFeMIB 2 }
  fcFeMIBCompliances  OBJECT IDENTIFIER ::= { fcFeMIBConformance 1 }
  fcFeMIBGroups       OBJECT IDENTIFIER ::= { fcFeMIBConformance 2 }

  fcFeMIBMinimumCompliance   MODULE-COMPLIANCE
      STATUS   current
      MODULE  -- this module
      MANDATORY-GROUPS { fcFeConfigGroup, fcFeStatusGroup,
                         fcFeErrorGroup }

      OBJECT        fcFeFabricName
      MIN-ACCESS    read-only

      OBJECT        fcFeElementName
      MIN-ACCESS    read-only

      OBJECT        fcFeModuleName
      MIN-ACCESS    read-only

      OBJECT        fcFxPortAdminMode
      MIN-ACCESS    read-only

      OBJECT        fcFxPortPhysAdminStatus
      MIN-ACCESS    read-only

      OBJECT        fcFxPortPhysRttov
      MIN-ACCESS    read-only

      OBJECT        fcFxPortBbCreditModel
      MIN-ACCESS    read-only





   ::= { fcFeMIBCompliances 1 }

  fcFeMIBFullCompliance   MODULE-COMPLIANCE
      STATUS   current
      MODULE  -- this module
      MANDATORY-GROUPS { fcFeConfigGroup, fcFeStatusGroup,
                         fcFeErrorGroup,  fcFeCapabilitiesGroup }

      GROUP fcFeClass1AccountingGroup

      GROUP fcFeClass2AccountingGroup

      GROUP fcFeClass3AccountingGroup

      OBJECT        fcFeFabricName
      MIN-ACCESS    read-only

      OBJECT        fcFeElementName
      MIN-ACCESS    read-only

      OBJECT        fcFeModuleName
      MIN-ACCESS    read-only

      OBJECT        fcFxPortAdminMode
      MIN-ACCESS    read-only

      OBJECT        fcFxPortPhysAdminStatus
      MIN-ACCESS    read-only






      OBJECT        fcFxPortPhysRttov
      MIN-ACCESS    read-only

      OBJECT        fcFxPortBbCreditModel
      MIN-ACCESS    read-only

   ::= { fcFeMIBCompliances 2 }

   fcFeConfigGroup  OBJECT-GROUP
      OBJECTS { fcFeFabricName, fcFeElementName, fcFeModuleCapacity,
                fcFeModuleDescr, fcFeModuleObjectID,
                fcFeModuleOperStatus, fcFeModuleLastChange,
                fcFeModuleFxPortCapacity, fcFeModuleName,
                fcFxPortName, fcFxPortFcphVersionHigh,
                fcFxPortFcphVersionLow, fcFxPortBbCredit,
                fcFxPortRxBufSize, fcFxPortRatov, fcFxPortEdtov,
                fcFxPortCosSupported, fcFxPortIntermixSupported,
                fcFxPortStackedConnMode, fcFxPortClass2SeqDeliv,
                fcFxPortClass3SeqDeliv, fcFxPortHoldTime }
      STATUS    current
   ::= { fcFeMIBGroups 1 }

  fcFeStatusGroup  OBJECT-GROUP
     OBJECTS { fcFxPortID, fcFxPortBbCreditAvailable,
               fcFxPortOperMode, fcFxPortAdminMode,
               fcFxPortPhysAdminStatus, fcFxPortPhysOperStatus,
               fcFxPortPhysLastChange, fcFxPortPhysRttov,
               fcFxPortFcphVersionAgreed, fcFxPortNxPortBbCredit,
               fcFxPortNxPortRxDataFieldSize, fcFxPortCosSuppAgreed,
               fcFxPortIntermixSuppAgreed,
               fcFxPortStackedConnModeAgreed,
               fcFxPortClass2SeqDelivAgreed,
               fcFxPortClass3SeqDelivAgreed,
               fcFxPortNxPortName, fcFxPortConnectedNxPort,
               fcFxPortBbCreditModel }
     STATUS    current
   ::= { fcFeMIBGroups 2 }

   fcFeErrorGroup  OBJECT-GROUP
      OBJECTS { fcFxPortLinkFailures, fcFxPortSyncLosses,
                fcFxPortSigLosses, fcFxPortPrimSeqProtoErrors,
                fcFxPortInvalidTxWords, fcFxPortInvalidCrcs,
                fcFxPortDelimiterErrors, fcFxPortAddressIdErrors,
                fcFxPortLinkResetIns, fcFxPortLinkResetOuts,
                fcFxPortOlsIns, fcFxPortOlsOuts }
      STATUS    current
   ::= { fcFeMIBGroups 3 }

   fcFeClass1AccountingGroup  OBJECT-GROUP
      OBJECTS { fcFxPortC1InFrames, fcFxPortC1OutFrames,
                fcFxPortC1InOctets, fcFxPortC1OutOctets,
                fcFxPortC1Discards, fcFxPortC1FbsyFrames,
                fcFxPortC1FrjtFrames, fcFxPortC1InConnections,
                fcFxPortC1OutConnections, fcFxPortC1ConnTime
      }
      STATUS    current
   ::= { fcFeMIBGroups 4 }

   fcFeClass2AccountingGroup  OBJECT-GROUP
      OBJECTS { fcFxPortC2InFrames, fcFxPortC2OutFrames,
                fcFxPortC2InOctets, fcFxPortC2OutOctets,
                fcFxPortC2Discards, fcFxPortC2FbsyFrames,
                fcFxPortC2FrjtFrames
      }
      STATUS    current
   ::= { fcFeMIBGroups 5 }

   fcFeClass3AccountingGroup  OBJECT-GROUP
      OBJECTS { fcFxPortC3InFrames, fcFxPortC3OutFrames,
                fcFxPortC3InOctets, fcFxPortC3OutOctets,
                fcFxPortC3Discards
      }





      STATUS    current
   ::= { fcFeMIBGroups 6 }

  fcFeCapabilitiesGroup  OBJECT-GROUP
     OBJECTS { fcFxPortCapFcphVersionHigh, fcFxPortCapFcphVersionLow,
               fcFxPortCapBbCreditMax, fcFxPortCapBbCreditMin,
               fcFxPortCapRxDataFieldSizeMax,
               fcFxPortCapRxDataFieldSizeMin,
               fcFxPortCapCos, fcFxPortCapIntermix,
               fcFxPortCapStackedConnMode, fcFxPortCapClass2SeqDeliv,
               fcFxPortCapClass3SeqDeliv, fcFxPortCapHoldTimeMax,
               fcFxPortCapHoldTimeMin
     }
     STATUS    current
   ::= { fcFeMIBGroups 7 }


  END
