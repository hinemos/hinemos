NHRP-MIB DEFINITIONS ::= BEGIN

   IMPORTS

       OBJECT-TYPE, MODULE-IDENTITY, mib-2, Integer32,
       Counter32, Unsigned32
           FROM SNMPv2-SMI
       MODULE-COMPLIANCE, OBJECT-GROUP
           FROM SNMPv2-CONF
       TEXTUAL-CONVENTION, TruthValue, RowStatus, StorageType,
       TimeStamp
           FROM SNMPv2-TC
       ifIndex
           FROM IF-MIB
       AddressFamilyNumbers
           FROM IANA-ADDRESS-FAMILY-NUMBERS-MIB
       ;

   nhrpMIB MODULE-IDENTITY
       LAST-UPDATED "9908260000Z"  -- August 26, 1999
       ORGANIZATION "Internetworking Over NBMA (ion) Working Group"












       ::= { mib-2 71 }


    NhrpGenAddr ::= TEXTUAL-CONVENTION
        STATUS      current
        SYNTAX      OCTET STRING (SIZE (0..64))

    nhrpObjects OBJECT IDENTIFIER ::= { nhrpMIB 1 }


    nhrpGeneralObjects OBJECT IDENTIFIER ::= { nhrpObjects 1 }



    nhrpNextIndex   OBJECT-TYPE
        SYNTAX      Unsigned32
        MAX-ACCESS  read-only
        STATUS      current
        ::= { nhrpGeneralObjects 1 }



        nhrpCacheTable OBJECT-TYPE
            SYNTAX      SEQUENCE OF NhrpCacheEntry
            MAX-ACCESS  not-accessible
            STATUS      current

       ::= { nhrpGeneralObjects 2 }

   nhrpCacheEntry OBJECT-TYPE
       SYNTAX      NhrpCacheEntry
       MAX-ACCESS  not-accessible
       STATUS      current
       INDEX       {
                       nhrpCacheInternetworkAddrType,
                       nhrpCacheInternetworkAddr,
                       ifIndex,
                       nhrpCacheIndex
                   }
       ::= { nhrpCacheTable 1 }

   NhrpCacheEntry ::= SEQUENCE {
       nhrpCacheInternetworkAddrType    AddressFamilyNumbers,
       nhrpCacheInternetworkAddr        NhrpGenAddr,
       nhrpCacheIndex                   Unsigned32,
       nhrpCachePrefixLength            Integer32,
       nhrpCacheNextHopInternetworkAddr NhrpGenAddr,
       nhrpCacheNbmaAddrType            AddressFamilyNumbers,
       nhrpCacheNbmaAddr                NhrpGenAddr,
       nhrpCacheNbmaSubaddr             NhrpGenAddr,
       nhrpCacheType                    INTEGER,
       nhrpCacheState                   INTEGER,
       nhrpCacheHoldingTimeValid        TruthValue,
       nhrpCacheHoldingTime             Unsigned32,
       nhrpCacheNegotiatedMtu           Integer32,
       nhrpCachePreference              Integer32,
       nhrpCacheStorageType             StorageType,
       nhrpCacheRowStatus               RowStatus


   }

   nhrpCacheInternetworkAddrType OBJECT-TYPE
       SYNTAX      AddressFamilyNumbers
       MAX-ACCESS  not-accessible
       STATUS      current
       ::= { nhrpCacheEntry 1 }

   nhrpCacheInternetworkAddr OBJECT-TYPE
       SYNTAX      NhrpGenAddr
       MAX-ACCESS  not-accessible
       STATUS      current





       ::= { nhrpCacheEntry 2 }

   nhrpCacheIndex OBJECT-TYPE
       SYNTAX      Unsigned32 (1..4294967295)
       MAX-ACCESS  not-accessible
       STATUS      current
       ::= { nhrpCacheEntry 3 }

   nhrpCachePrefixLength OBJECT-TYPE
       SYNTAX      Integer32 (0..255)
       MAX-ACCESS  read-only
       STATUS      current
       ::= { nhrpCacheEntry 4 }

   nhrpCacheNextHopInternetworkAddr OBJECT-TYPE
       SYNTAX      NhrpGenAddr
       MAX-ACCESS  read-create
       STATUS      current

       ::= { nhrpCacheEntry 5 }

   nhrpCacheNbmaAddrType OBJECT-TYPE
       SYNTAX      AddressFamilyNumbers
       MAX-ACCESS  read-create
       STATUS      current
       ::= { nhrpCacheEntry 6 }







   nhrpCacheNbmaAddr OBJECT-TYPE
       SYNTAX      NhrpGenAddr
       MAX-ACCESS  read-create
       STATUS      current
       ::= { nhrpCacheEntry 7 }

   nhrpCacheNbmaSubaddr OBJECT-TYPE
       SYNTAX      NhrpGenAddr
       MAX-ACCESS  read-create
       STATUS      current
       ::= { nhrpCacheEntry 8 }

   nhrpCacheType OBJECT-TYPE
       SYNTAX      INTEGER {
                       other(1),
                       register(2),
                       resolveAuthoritative(3),
                       resoveNonauthoritative(4),
                       transit(5),
                       administrativelyAdded(6),
                       atmarp(7),
                       scsp(8)
                   }
       MAX-ACCESS  read-create
       STATUS      current
       ::= { nhrpCacheEntry 9 }


   nhrpCacheState OBJECT-TYPE
       SYNTAX      INTEGER {
                       incomplete(1),
                       ackReply(2),
                       nakReply(3)
                   }
       MAX-ACCESS  read-only
       STATUS      current
       ::= { nhrpCacheEntry 10 }

   nhrpCacheHoldingTimeValid OBJECT-TYPE
       SYNTAX      TruthValue
       MAX-ACCESS  read-only
       STATUS      current
       ::= { nhrpCacheEntry 11 }

   nhrpCacheHoldingTime OBJECT-TYPE
       SYNTAX      Unsigned32(0..65535)
       UNITS       "seconds"
       MAX-ACCESS  read-only
       STATUS      current
       ::= { nhrpCacheEntry 12 }








   nhrpCacheNegotiatedMtu OBJECT-TYPE
       SYNTAX      Integer32 (0..65535)
       MAX-ACCESS  read-only
       STATUS      current
       ::= { nhrpCacheEntry 13 }

   nhrpCachePreference OBJECT-TYPE
       SYNTAX      Integer32 (0..255)
       MAX-ACCESS  read-create
       STATUS      current
       ::= { nhrpCacheEntry 14 }

   nhrpCacheStorageType OBJECT-TYPE
       SYNTAX      StorageType
       MAX-ACCESS  read-create
       STATUS      current
       DEFVAL      { nonVolatile }
       ::= { nhrpCacheEntry 15 }








   nhrpCacheRowStatus OBJECT-TYPE
       SYNTAX      RowStatus
       MAX-ACCESS  read-create
       STATUS      current
       ::= { nhrpCacheEntry 16 }


   nhrpPurgeReqTable OBJECT-TYPE
       SYNTAX      SEQUENCE OF NhrpPurgeReqEntry
       MAX-ACCESS  not-accessible
       STATUS      current
       ::= { nhrpGeneralObjects 3 }

   nhrpPurgeReqEntry OBJECT-TYPE
       SYNTAX      NhrpPurgeReqEntry
       MAX-ACCESS  not-accessible
       STATUS      current
       INDEX       {   nhrpPurgeIndex  }
       ::= { nhrpPurgeReqTable 1 }

   NhrpPurgeReqEntry ::= SEQUENCE {
       nhrpPurgeIndex                        Unsigned32,
       nhrpPurgeCacheIdentifier              Unsigned32,
       nhrpPurgePrefixLength                 Integer32,
       nhrpPurgeRequestID                    Unsigned32,
       nhrpPurgeReplyExpected                TruthValue,
       nhrpPurgeRowStatus                    RowStatus
   }

   nhrpPurgeIndex  OBJECT-TYPE
       SYNTAX      Unsigned32 (1..4294967295)
       MAX-ACCESS  not-accessible
       STATUS      current
       ::= { nhrpPurgeReqEntry 1 }






   nhrpPurgeCacheIdentifier OBJECT-TYPE
       SYNTAX      Unsigned32 (1..4294967295)
       MAX-ACCESS  read-create
       STATUS      current

       ::= { nhrpPurgeReqEntry 2 }

   nhrpPurgePrefixLength OBJECT-TYPE
       SYNTAX      Integer32 (0..255)
       MAX-ACCESS  read-only
       STATUS      current
       ::= { nhrpPurgeReqEntry 3 }

   nhrpPurgeRequestID OBJECT-TYPE
       SYNTAX      Unsigned32
       MAX-ACCESS  read-create
       STATUS      current
       ::= { nhrpPurgeReqEntry 4 }

   nhrpPurgeReplyExpected OBJECT-TYPE
       SYNTAX      TruthValue
       MAX-ACCESS  read-create
       STATUS      current
       ::= { nhrpPurgeReqEntry 5 }

   nhrpPurgeRowStatus OBJECT-TYPE
       SYNTAX      RowStatus
       MAX-ACCESS  read-create
       STATUS      current
       ::= { nhrpPurgeReqEntry 6 }






   nhrpClientObjects OBJECT IDENTIFIER ::= { nhrpObjects 2 }


   nhrpClientTable OBJECT-TYPE
       SYNTAX      SEQUENCE OF NhrpClientEntry
       MAX-ACCESS  not-accessible
       STATUS      current
       ::= { nhrpClientObjects 1 }

   nhrpClientEntry OBJECT-TYPE
       SYNTAX      NhrpClientEntry
       MAX-ACCESS  not-accessible
       STATUS      current
       INDEX       { nhrpClientIndex }
       ::= { nhrpClientTable 1 }

   NhrpClientEntry ::= SEQUENCE {
       nhrpClientIndex                      Unsigned32,
       nhrpClientInternetworkAddrType       AddressFamilyNumbers,
       nhrpClientInternetworkAddr           NhrpGenAddr,
       nhrpClientNbmaAddrType               AddressFamilyNumbers,
       nhrpClientNbmaAddr                   NhrpGenAddr,
       nhrpClientNbmaSubaddr                NhrpGenAddr,
       nhrpClientInitialRequestTimeout      Integer32,
       nhrpClientRegistrationRequestRetries Integer32,
       nhrpClientResolutionRequestRetries   Integer32,
       nhrpClientPurgeRequestRetries        Integer32,
       nhrpClientDefaultMtu                 Unsigned32,
       nhrpClientHoldTime                   Unsigned32,
       nhrpClientRequestID                  Unsigned32,
       nhrpClientStorageType                StorageType,
       nhrpClientRowStatus                  RowStatus
   }








   nhrpClientIndex OBJECT-TYPE
       SYNTAX      Unsigned32 (1..4294967295)
       MAX-ACCESS  not-accessible
       STATUS      current

       ::= { nhrpClientEntry 1 }

   nhrpClientInternetworkAddrType OBJECT-TYPE
       SYNTAX      AddressFamilyNumbers
       MAX-ACCESS  read-create
       STATUS      current
       ::= { nhrpClientEntry 2 }

   nhrpClientInternetworkAddr OBJECT-TYPE
       SYNTAX      NhrpGenAddr
       MAX-ACCESS  read-create
       STATUS      current
       ::= { nhrpClientEntry 3 }

   nhrpClientNbmaAddrType OBJECT-TYPE
       SYNTAX      AddressFamilyNumbers
       MAX-ACCESS  read-create
       STATUS      current
       ::= { nhrpClientEntry 4 }

   nhrpClientNbmaAddr OBJECT-TYPE
       SYNTAX      NhrpGenAddr
       MAX-ACCESS  read-create
       STATUS      current






       ::= { nhrpClientEntry 5 }

   nhrpClientNbmaSubaddr OBJECT-TYPE
       SYNTAX      NhrpGenAddr
       MAX-ACCESS  read-create
       STATUS      current
       ::= { nhrpClientEntry 6 }

   nhrpClientInitialRequestTimeout OBJECT-TYPE
       SYNTAX      Integer32 (1..900)
       UNITS       "seconds"
       MAX-ACCESS  read-create
       STATUS      current
       DEFVAL      { 10 }
       ::= { nhrpClientEntry 7 }

   nhrpClientRegistrationRequestRetries OBJECT-TYPE
       SYNTAX      Integer32 (0..65535)
       MAX-ACCESS  read-create
       STATUS      current
       DEFVAL      { 3 }
       ::= { nhrpClientEntry 8 }

   nhrpClientResolutionRequestRetries OBJECT-TYPE
       SYNTAX      Integer32 (0..65535)
       MAX-ACCESS  read-create
       STATUS      current
       DEFVAL      { 3 }
       ::= { nhrpClientEntry 9 }





   nhrpClientPurgeRequestRetries OBJECT-TYPE
       SYNTAX      Integer32 (0..65535)
       MAX-ACCESS  read-create
       STATUS      current
       DEFVAL      { 3 }
       ::= { nhrpClientEntry 10 }

   nhrpClientDefaultMtu OBJECT-TYPE
       SYNTAX      Unsigned32 (0..65535)
       MAX-ACCESS  read-create
       STATUS      current

       DEFVAL      { 9180 }
       ::= { nhrpClientEntry 11 }

   nhrpClientHoldTime OBJECT-TYPE
       SYNTAX      Unsigned32(0..65535)
       UNITS       "seconds"
       MAX-ACCESS  read-create
       STATUS      current
       DEFVAL      { 900 }
       ::= { nhrpClientEntry 12 }

   nhrpClientRequestID OBJECT-TYPE
       SYNTAX      Unsigned32
       MAX-ACCESS  read-create
       STATUS      current
       ::= { nhrpClientEntry 13 }

   nhrpClientStorageType OBJECT-TYPE
       SYNTAX      StorageType
       MAX-ACCESS  read-create
       STATUS      current
       DEFVAL      { nonVolatile }
       ::= { nhrpClientEntry 14 }

   nhrpClientRowStatus OBJECT-TYPE
       SYNTAX      RowStatus
       MAX-ACCESS  read-create
       STATUS      current
       ::= { nhrpClientEntry 15 }



   nhrpClientRegistrationTable OBJECT-TYPE
       SYNTAX      SEQUENCE OF NhrpClientRegistrationEntry
       MAX-ACCESS  not-accessible
       STATUS      current
       ::= { nhrpClientObjects 2 }

   nhrpClientRegistrationEntry OBJECT-TYPE
       SYNTAX      NhrpClientRegistrationEntry
       MAX-ACCESS  not-accessible
       STATUS      current






       INDEX       { nhrpClientIndex,
                     nhrpClientRegIndex
                   }
       ::= { nhrpClientRegistrationTable 1 }

   NhrpClientRegistrationEntry ::= SEQUENCE {
       nhrpClientRegIndex          Unsigned32,
       nhrpClientRegUniqueness     INTEGER,
       nhrpClientRegState          INTEGER,
       nhrpClientRegRowStatus      RowStatus
   }

   nhrpClientRegIndex OBJECT-TYPE
       SYNTAX      Unsigned32 (1..4294967295)
       MAX-ACCESS  not-accessible
       STATUS      current
       ::= { nhrpClientRegistrationEntry 1 }

   nhrpClientRegUniqueness OBJECT-TYPE
       SYNTAX      INTEGER {
                       requestUnique(1),
                       requestNotUnique(2)
                   }
       MAX-ACCESS  read-create
       STATUS      current
       ::= { nhrpClientRegistrationEntry 2 }

   nhrpClientRegState  OBJECT-TYPE
       SYNTAX      INTEGER {
                       other(1),
                       registering(2),
                       ackRegisterReply(3),
                       nakRegisterReply(4)





                   }
       MAX-ACCESS  read-only
       STATUS      current
       ::= { nhrpClientRegistrationEntry 3 }

   nhrpClientRegRowStatus OBJECT-TYPE

       SYNTAX      RowStatus
       MAX-ACCESS  read-create
       STATUS      current
       ::= { nhrpClientRegistrationEntry 4 }


   nhrpClientNhsTable OBJECT-TYPE
       SYNTAX      SEQUENCE OF NhrpClientNhsEntry
       MAX-ACCESS  not-accessible
       STATUS      current
       ::= { nhrpClientObjects 3 }







   nhrpClientNhsEntry OBJECT-TYPE
       SYNTAX      NhrpClientNhsEntry
       MAX-ACCESS  not-accessible
       STATUS      current
       INDEX       { nhrpClientIndex, nhrpClientNhsIndex }
       ::= { nhrpClientNhsTable 1 }

   NhrpClientNhsEntry ::= SEQUENCE {
       nhrpClientNhsIndex                  Unsigned32,
       nhrpClientNhsInternetworkAddrType   AddressFamilyNumbers,
       nhrpClientNhsInternetworkAddr       NhrpGenAddr,
       nhrpClientNhsNbmaAddrType           AddressFamilyNumbers,
       nhrpClientNhsNbmaAddr               NhrpGenAddr,
       nhrpClientNhsNbmaSubaddr            NhrpGenAddr,
       nhrpClientNhsInUse                  TruthValue,
       nhrpClientNhsRowStatus              RowStatus
   }

   nhrpClientNhsIndex OBJECT-TYPE
       SYNTAX      Unsigned32 (1..4294967295)
       MAX-ACCESS  not-accessible
       STATUS      current
       ::= { nhrpClientNhsEntry 1 }

   nhrpClientNhsInternetworkAddrType OBJECT-TYPE
       SYNTAX      AddressFamilyNumbers
       MAX-ACCESS  read-create
       STATUS      current
       ::= { nhrpClientNhsEntry 2 }

   nhrpClientNhsInternetworkAddr OBJECT-TYPE
       SYNTAX      NhrpGenAddr
       MAX-ACCESS  read-create
       STATUS      current
       ::= { nhrpClientNhsEntry 3 }

   nhrpClientNhsNbmaAddrType OBJECT-TYPE
       SYNTAX      AddressFamilyNumbers
       MAX-ACCESS  read-create
       STATUS      current
       ::= { nhrpClientNhsEntry 4 }

   nhrpClientNhsNbmaAddr OBJECT-TYPE
       SYNTAX      NhrpGenAddr
       MAX-ACCESS  read-create
       STATUS      current
       ::= { nhrpClientNhsEntry 5 }

   nhrpClientNhsNbmaSubaddr OBJECT-TYPE
       SYNTAX      NhrpGenAddr
       MAX-ACCESS  read-create
       STATUS      current
       ::= { nhrpClientNhsEntry 6 }

   nhrpClientNhsInUse OBJECT-TYPE
       SYNTAX      TruthValue
       MAX-ACCESS  read-only
       STATUS      current
       ::= { nhrpClientNhsEntry 7 }

   nhrpClientNhsRowStatus OBJECT-TYPE
       SYNTAX      RowStatus
       MAX-ACCESS  read-create
       STATUS      current






       ::= { nhrpClientNhsEntry 8 }


   nhrpClientStatTable OBJECT-TYPE
       SYNTAX      SEQUENCE OF NhrpClientStatEntry
       MAX-ACCESS  not-accessible
       STATUS      current
       ::= { nhrpClientObjects 4 }

   nhrpClientStatEntry OBJECT-TYPE
       SYNTAX      NhrpClientStatEntry
       MAX-ACCESS  not-accessible
       STATUS      current
       INDEX       { nhrpClientIndex }
       ::= { nhrpClientStatTable 1 }

   NhrpClientStatEntry ::= SEQUENCE {
       nhrpClientStatTxResolveReq                    Counter32,
       nhrpClientStatRxResolveReplyAck               Counter32,
       nhrpClientStatRxResolveReplyNakProhibited     Counter32,
       nhrpClientStatRxResolveReplyNakInsufResources Counter32,
       nhrpClientStatRxResolveReplyNakNoBinding      Counter32,
       nhrpClientStatRxResolveReplyNakNotUnique      Counter32,
       nhrpClientStatTxRegisterReq                   Counter32,
       nhrpClientStatRxRegisterAck                   Counter32,
       nhrpClientStatRxRegisterNakProhibited         Counter32,
       nhrpClientStatRxRegisterNakInsufResources     Counter32,
       nhrpClientStatRxRegisterNakAlreadyReg         Counter32,

       nhrpClientStatRxPurgeReq                      Counter32,
       nhrpClientStatTxPurgeReq                      Counter32,
       nhrpClientStatRxPurgeReply                    Counter32,
       nhrpClientStatTxPurgeReply                    Counter32,

       nhrpClientStatTxErrorIndication               Counter32,
       nhrpClientStatRxErrUnrecognizedExtension      Counter32,
       nhrpClientStatRxErrLoopDetected               Counter32,





       nhrpClientStatRxErrProtoAddrUnreachable       Counter32,
       nhrpClientStatRxErrProtoError                 Counter32,
       nhrpClientStatRxErrSduSizeExceeded            Counter32,
       nhrpClientStatRxErrInvalidExtension           Counter32,
       nhrpClientStatRxErrAuthenticationFailure      Counter32,
       nhrpClientStatRxErrHopCountExceeded           Counter32,
       nhrpClientStatDiscontinuityTime               TimeStamp
   }

   nhrpClientStatTxResolveReq OBJECT-TYPE
       SYNTAX      Counter32
       MAX-ACCESS  read-only
       STATUS      current
       ::= { nhrpClientStatEntry 1 }

   nhrpClientStatRxResolveReplyAck OBJECT-TYPE
       SYNTAX      Counter32
       MAX-ACCESS  read-only
       STATUS      current
       ::= { nhrpClientStatEntry 2 }

   nhrpClientStatRxResolveReplyNakProhibited OBJECT-TYPE
       SYNTAX      Counter32
       MAX-ACCESS  read-only
       STATUS      current
       ::= { nhrpClientStatEntry 3 }

   nhrpClientStatRxResolveReplyNakInsufResources OBJECT-TYPE
       SYNTAX      Counter32
       MAX-ACCESS  read-only
       STATUS      current
       ::= { nhrpClientStatEntry 4 }

   nhrpClientStatRxResolveReplyNakNoBinding OBJECT-TYPE
       SYNTAX      Counter32
       MAX-ACCESS  read-only
       STATUS      current

       ::= { nhrpClientStatEntry 5 }

   nhrpClientStatRxResolveReplyNakNotUnique OBJECT-TYPE
       SYNTAX      Counter32
       MAX-ACCESS  read-only
       STATUS      current








       ::= { nhrpClientStatEntry 6 }

   nhrpClientStatTxRegisterReq OBJECT-TYPE
       SYNTAX      Counter32
       MAX-ACCESS  read-only
       STATUS      current
       ::= { nhrpClientStatEntry 7 }

   nhrpClientStatRxRegisterAck OBJECT-TYPE
       SYNTAX      Counter32
       MAX-ACCESS  read-only
       STATUS      current
       ::= { nhrpClientStatEntry 8 }

   nhrpClientStatRxRegisterNakProhibited OBJECT-TYPE
       SYNTAX      Counter32
       MAX-ACCESS  read-only
       STATUS      current







       ::= { nhrpClientStatEntry 9 }

   nhrpClientStatRxRegisterNakInsufResources OBJECT-TYPE
       SYNTAX      Counter32
       MAX-ACCESS  read-only
       STATUS      current
       ::= { nhrpClientStatEntry 10 }

   nhrpClientStatRxRegisterNakAlreadyReg OBJECT-TYPE
       SYNTAX      Counter32
       MAX-ACCESS  read-only
       STATUS      current
       ::= { nhrpClientStatEntry 11 }

   nhrpClientStatRxPurgeReq OBJECT-TYPE
       SYNTAX      Counter32
       MAX-ACCESS  read-only
       STATUS      current





       ::= { nhrpClientStatEntry 12 }

   nhrpClientStatTxPurgeReq OBJECT-TYPE
       SYNTAX      Counter32
       MAX-ACCESS  read-only
       STATUS      current
       ::= { nhrpClientStatEntry 13 }

   nhrpClientStatRxPurgeReply OBJECT-TYPE
       SYNTAX      Counter32
       MAX-ACCESS  read-only
       STATUS      current
       ::= { nhrpClientStatEntry 14 }

   nhrpClientStatTxPurgeReply OBJECT-TYPE
       SYNTAX      Counter32
       MAX-ACCESS  read-only
       STATUS      current
       ::= { nhrpClientStatEntry 15 }

   nhrpClientStatTxErrorIndication OBJECT-TYPE
       SYNTAX      Counter32
       MAX-ACCESS  read-only
       STATUS      current
       ::= { nhrpClientStatEntry 16 }

   nhrpClientStatRxErrUnrecognizedExtension OBJECT-TYPE
       SYNTAX      Counter32
       MAX-ACCESS  read-only
       STATUS      current
       ::= { nhrpClientStatEntry 17 }

   nhrpClientStatRxErrLoopDetected OBJECT-TYPE
       SYNTAX      Counter32
       MAX-ACCESS  read-only
       STATUS      current







       ::= { nhrpClientStatEntry 18 }

   nhrpClientStatRxErrProtoAddrUnreachable OBJECT-TYPE
       SYNTAX      Counter32
       MAX-ACCESS  read-only
       STATUS      current
       ::= { nhrpClientStatEntry 19 }

   nhrpClientStatRxErrProtoError OBJECT-TYPE
       SYNTAX      Counter32
       MAX-ACCESS  read-only
       STATUS      current
       ::= { nhrpClientStatEntry 20 }






   nhrpClientStatRxErrSduSizeExceeded OBJECT-TYPE
       SYNTAX      Counter32
       MAX-ACCESS  read-only
       STATUS      current
       ::= { nhrpClientStatEntry 21 }

   nhrpClientStatRxErrInvalidExtension OBJECT-TYPE
       SYNTAX      Counter32
       MAX-ACCESS  read-only
       STATUS      current
       ::= { nhrpClientStatEntry 22 }

   nhrpClientStatRxErrAuthenticationFailure OBJECT-TYPE
       SYNTAX      Counter32
       MAX-ACCESS  read-only
       STATUS      current
       ::= { nhrpClientStatEntry 23 }

   nhrpClientStatRxErrHopCountExceeded OBJECT-TYPE
       SYNTAX      Counter32
       MAX-ACCESS  read-only
       STATUS      current

       ::= { nhrpClientStatEntry 24 }

   nhrpClientStatDiscontinuityTime OBJECT-TYPE
       SYNTAX      TimeStamp
       MAX-ACCESS  read-only
       STATUS      current
       ::= { nhrpClientStatEntry 25 }












   nhrpServerObjects OBJECT IDENTIFIER ::= { nhrpObjects 3 }


   nhrpServerTable OBJECT-TYPE
       SYNTAX      SEQUENCE OF NhrpServerEntry
       MAX-ACCESS  not-accessible
       STATUS      current
       ::= { nhrpServerObjects 1 }

   nhrpServerEntry OBJECT-TYPE
       SYNTAX      NhrpServerEntry
       MAX-ACCESS  not-accessible
       STATUS      current
       INDEX       { nhrpServerIndex }
       ::= { nhrpServerTable 1 }

   NhrpServerEntry ::= SEQUENCE {
       nhrpServerIndex                 Unsigned32,
       nhrpServerInternetworkAddrType  AddressFamilyNumbers,
       nhrpServerInternetworkAddr      NhrpGenAddr,
       nhrpServerNbmaAddrType          AddressFamilyNumbers,
       nhrpServerNbmaAddr              NhrpGenAddr,
       nhrpServerNbmaSubaddr           NhrpGenAddr,
       nhrpServerStorageType           StorageType,
       nhrpServerRowStatus             RowStatus
   }

   nhrpServerIndex OBJECT-TYPE
       SYNTAX      Unsigned32 (1..4294967295)
       MAX-ACCESS  not-accessible
       STATUS      current
       ::= { nhrpServerEntry 1 }






   nhrpServerInternetworkAddrType OBJECT-TYPE
       SYNTAX      AddressFamilyNumbers
       MAX-ACCESS  read-create
       STATUS      current
       ::= { nhrpServerEntry 2 }

   nhrpServerInternetworkAddr OBJECT-TYPE
       SYNTAX      NhrpGenAddr
       MAX-ACCESS  read-create
       STATUS      current
       ::= { nhrpServerEntry 3 }

   nhrpServerNbmaAddrType OBJECT-TYPE
       SYNTAX      AddressFamilyNumbers
       MAX-ACCESS  read-create
       STATUS      current
       ::= { nhrpServerEntry 4 }

   nhrpServerNbmaAddr OBJECT-TYPE
       SYNTAX      NhrpGenAddr
       MAX-ACCESS  read-create
       STATUS      current
       ::= { nhrpServerEntry 5 }

   nhrpServerNbmaSubaddr OBJECT-TYPE
       SYNTAX      NhrpGenAddr
       MAX-ACCESS  read-create
       STATUS      current
       ::= { nhrpServerEntry 6 }






   nhrpServerStorageType OBJECT-TYPE
       SYNTAX      StorageType
       MAX-ACCESS  read-create
       STATUS      current
       DEFVAL      { nonVolatile }
       ::= { nhrpServerEntry 7 }

   nhrpServerRowStatus OBJECT-TYPE
       SYNTAX      RowStatus
       MAX-ACCESS  read-create
       STATUS      current
       ::= { nhrpServerEntry 8 }

   nhrpServerCacheTable OBJECT-TYPE
       SYNTAX      SEQUENCE OF NhrpServerCacheEntry
       MAX-ACCESS  not-accessible
       STATUS      current
       ::= { nhrpServerObjects 2 }

   nhrpServerCacheEntry OBJECT-TYPE
       SYNTAX      NhrpServerCacheEntry
       MAX-ACCESS  not-accessible
       STATUS      current






       INDEX       {
                       nhrpCacheInternetworkAddrType,
                       nhrpCacheInternetworkAddr,
                       ifIndex,
                       nhrpCacheIndex
                   }
       ::= { nhrpServerCacheTable 1 }

   NhrpServerCacheEntry ::= SEQUENCE {
       nhrpServerCacheAuthoritative   TruthValue,
       nhrpServerCacheUniqueness      TruthValue
   }

   nhrpServerCacheAuthoritative OBJECT-TYPE
       SYNTAX      TruthValue
       MAX-ACCESS  read-only
       STATUS      current
       ::= { nhrpServerCacheEntry 1 }

   nhrpServerCacheUniqueness OBJECT-TYPE
       SYNTAX      TruthValue
       MAX-ACCESS  read-create
       STATUS      current
       ::= { nhrpServerCacheEntry 2 }


   nhrpServerNhcTable OBJECT-TYPE
       SYNTAX      SEQUENCE OF NhrpServerNhcEntry
       MAX-ACCESS  not-accessible
       STATUS      current







       ::= { nhrpServerObjects 3 }

   nhrpServerNhcEntry OBJECT-TYPE
       SYNTAX      NhrpServerNhcEntry
       MAX-ACCESS  not-accessible
       STATUS      current
       INDEX       { nhrpServerIndex, nhrpServerNhcIndex }
       ::= { nhrpServerNhcTable 1 }

   NhrpServerNhcEntry ::= SEQUENCE {
       nhrpServerNhcIndex                  Unsigned32,
       nhrpServerNhcPrefixLength           Integer32,
       nhrpServerNhcInternetworkAddrType   AddressFamilyNumbers,
       nhrpServerNhcInternetworkAddr       NhrpGenAddr,
       nhrpServerNhcNbmaAddrType           AddressFamilyNumbers,
       nhrpServerNhcNbmaAddr               NhrpGenAddr,
       nhrpServerNhcNbmaSubaddr            NhrpGenAddr,
       nhrpServerNhcInUse                  TruthValue,
       nhrpServerNhcRowStatus              RowStatus
   }

   nhrpServerNhcIndex OBJECT-TYPE
       SYNTAX      Unsigned32 (1..4294967295)
       MAX-ACCESS  not-accessible
       STATUS      current
       ::= { nhrpServerNhcEntry 1 }

   nhrpServerNhcPrefixLength OBJECT-TYPE
       SYNTAX      Integer32 (0..255)
       MAX-ACCESS  read-create
       STATUS      current
       ::= { nhrpServerNhcEntry 2 }







   nhrpServerNhcInternetworkAddrType OBJECT-TYPE
       SYNTAX      AddressFamilyNumbers
       MAX-ACCESS  read-create
       STATUS      current
       ::= { nhrpServerNhcEntry 3 }

   nhrpServerNhcInternetworkAddr OBJECT-TYPE
       SYNTAX      NhrpGenAddr
       MAX-ACCESS  read-create
       STATUS      current
       ::= { nhrpServerNhcEntry 4 }

   nhrpServerNhcNbmaAddrType OBJECT-TYPE
       SYNTAX      AddressFamilyNumbers
       MAX-ACCESS  read-create
       STATUS      current
       ::= { nhrpServerNhcEntry 5 }

   nhrpServerNhcNbmaAddr OBJECT-TYPE
       SYNTAX      NhrpGenAddr
       MAX-ACCESS  read-create
       STATUS      current
       ::= { nhrpServerNhcEntry 6 }

   nhrpServerNhcNbmaSubaddr OBJECT-TYPE
       SYNTAX      NhrpGenAddr
       MAX-ACCESS  read-create
       STATUS      current






       ::= { nhrpServerNhcEntry 7 }

   nhrpServerNhcInUse OBJECT-TYPE
       SYNTAX      TruthValue
       MAX-ACCESS  read-only
       STATUS      current
       ::= { nhrpServerNhcEntry 8 }

   nhrpServerNhcRowStatus OBJECT-TYPE
       SYNTAX      RowStatus
       MAX-ACCESS  read-create
       STATUS      current
       ::= { nhrpServerNhcEntry 9 }


   nhrpServerStatTable OBJECT-TYPE
       SYNTAX      SEQUENCE OF NhrpServerStatEntry
       MAX-ACCESS  not-accessible
       STATUS      current
       ::= { nhrpServerObjects 4 }

   nhrpServerStatEntry OBJECT-TYPE
       SYNTAX      NhrpServerStatEntry
       MAX-ACCESS  not-accessible
       STATUS      current
       INDEX       { nhrpServerIndex }
       ::= { nhrpServerStatTable 1 }







   NhrpServerStatEntry ::= SEQUENCE {
       nhrpServerStatRxResolveReq                    Counter32,
       nhrpServerStatTxResolveReplyAck               Counter32,
       nhrpServerStatTxResolveReplyNakProhibited     Counter32,
       nhrpServerStatTxResolveReplyNakInsufResources Counter32,
       nhrpServerStatTxResolveReplyNakNoBinding      Counter32,
       nhrpServerStatTxResolveReplyNakNotUnique      Counter32,

       nhrpServerStatRxRegisterReq                   Counter32,
       nhrpServerStatTxRegisterAck                   Counter32,
       nhrpServerStatTxRegisterNakProhibited         Counter32,
       nhrpServerStatTxRegisterNakInsufResources     Counter32,
       nhrpServerStatTxRegisterNakAlreadyReg         Counter32,

       nhrpServerStatRxPurgeReq                      Counter32,
       nhrpServerStatTxPurgeReq                      Counter32,
       nhrpServerStatRxPurgeReply                    Counter32,
       nhrpServerStatTxPurgeReply                    Counter32,

       nhrpServerStatRxErrUnrecognizedExtension      Counter32,
       nhrpServerStatRxErrLoopDetected               Counter32,
       nhrpServerStatRxErrProtoAddrUnreachable       Counter32,
       nhrpServerStatRxErrProtoError                 Counter32,
       nhrpServerStatRxErrSduSizeExceeded            Counter32,
       nhrpServerStatRxErrInvalidExtension           Counter32,
       nhrpServerStatRxErrInvalidResReplyReceived    Counter32,
       nhrpServerStatRxErrAuthenticationFailure      Counter32,
       nhrpServerStatRxErrHopCountExceeded           Counter32,

       nhrpServerStatTxErrUnrecognizedExtension      Counter32,
       nhrpServerStatTxErrLoopDetected               Counter32,
       nhrpServerStatTxErrProtoAddrUnreachable       Counter32,
       nhrpServerStatTxErrProtoError                 Counter32,
       nhrpServerStatTxErrSduSizeExceeded            Counter32,
       nhrpServerStatTxErrInvalidExtension           Counter32,
       nhrpServerStatTxErrAuthenticationFailure      Counter32,
       nhrpServerStatTxErrHopCountExceeded           Counter32,

       nhrpServerStatFwResolveReq                    Counter32,
       nhrpServerStatFwResolveReply                  Counter32,
       nhrpServerStatFwRegisterReq                   Counter32,
       nhrpServerStatFwRegisterReply                 Counter32,
       nhrpServerStatFwPurgeReq                      Counter32,
       nhrpServerStatFwPurgeReply                    Counter32,
       nhrpServerStatFwErrorIndication               Counter32,
       nhrpServerStatDiscontinuityTime               TimeStamp





   }

   nhrpServerStatRxResolveReq OBJECT-TYPE
       SYNTAX      Counter32
       MAX-ACCESS  read-only
       STATUS      current
       ::= { nhrpServerStatEntry 1 }

   nhrpServerStatTxResolveReplyAck OBJECT-TYPE
       SYNTAX      Counter32
       MAX-ACCESS  read-only
       STATUS      current
       ::= { nhrpServerStatEntry 2 }

   nhrpServerStatTxResolveReplyNakProhibited OBJECT-TYPE
       SYNTAX      Counter32
       MAX-ACCESS  read-only
       STATUS      current
       ::= { nhrpServerStatEntry 3 }






   nhrpServerStatTxResolveReplyNakInsufResources OBJECT-TYPE
       SYNTAX      Counter32
       MAX-ACCESS  read-only
       STATUS      current
       ::= { nhrpServerStatEntry 4 }

   nhrpServerStatTxResolveReplyNakNoBinding OBJECT-TYPE
       SYNTAX      Counter32
       MAX-ACCESS  read-only
       STATUS      current
       ::= { nhrpServerStatEntry 5 }

   nhrpServerStatTxResolveReplyNakNotUnique OBJECT-TYPE
       SYNTAX      Counter32
       MAX-ACCESS  read-only
       STATUS      current
       ::= { nhrpServerStatEntry 6 }





   nhrpServerStatRxRegisterReq OBJECT-TYPE
       SYNTAX      Counter32
       MAX-ACCESS  read-only
       STATUS      current
       ::= { nhrpServerStatEntry 7 }

   nhrpServerStatTxRegisterAck OBJECT-TYPE
       SYNTAX      Counter32
       MAX-ACCESS  read-only
       STATUS      current
       ::= { nhrpServerStatEntry 8 }

   nhrpServerStatTxRegisterNakProhibited OBJECT-TYPE
       SYNTAX      Counter32
       MAX-ACCESS  read-only
       STATUS      current
       ::= { nhrpServerStatEntry 9 }








   nhrpServerStatTxRegisterNakInsufResources OBJECT-TYPE
       SYNTAX      Counter32
       MAX-ACCESS  read-only
       STATUS      current
       ::= { nhrpServerStatEntry 10 }

   nhrpServerStatTxRegisterNakAlreadyReg OBJECT-TYPE
       SYNTAX      Counter32
       MAX-ACCESS  read-only
       STATUS      current
       ::= { nhrpServerStatEntry 11 }

   nhrpServerStatRxPurgeReq OBJECT-TYPE
       SYNTAX      Counter32
       MAX-ACCESS  read-only
       STATUS      current
       ::= { nhrpServerStatEntry 12 }






   nhrpServerStatTxPurgeReq OBJECT-TYPE
       SYNTAX      Counter32
       MAX-ACCESS  read-only
       STATUS      current
       ::= { nhrpServerStatEntry 13 }

   nhrpServerStatRxPurgeReply OBJECT-TYPE
       SYNTAX      Counter32
       MAX-ACCESS  read-only
       STATUS      current
       ::= { nhrpServerStatEntry 14 }

   nhrpServerStatTxPurgeReply OBJECT-TYPE
       SYNTAX      Counter32
       MAX-ACCESS  read-only
       STATUS      current
       ::= { nhrpServerStatEntry 15 }

   nhrpServerStatRxErrUnrecognizedExtension OBJECT-TYPE
       SYNTAX      Counter32
       MAX-ACCESS  read-only





       STATUS      current
       ::= { nhrpServerStatEntry 16 }


   nhrpServerStatRxErrLoopDetected OBJECT-TYPE
       SYNTAX      Counter32
       MAX-ACCESS  read-only
       STATUS      current
       ::= { nhrpServerStatEntry 17 }

   nhrpServerStatRxErrProtoAddrUnreachable OBJECT-TYPE
       SYNTAX      Counter32
       MAX-ACCESS  read-only
       STATUS      current





       ::= { nhrpServerStatEntry 18 }

   nhrpServerStatRxErrProtoError OBJECT-TYPE
       SYNTAX      Counter32
       MAX-ACCESS  read-only
       STATUS      current

       ::= { nhrpServerStatEntry 19 }

   nhrpServerStatRxErrSduSizeExceeded OBJECT-TYPE
       SYNTAX      Counter32
       MAX-ACCESS  read-only
       STATUS      current
       ::= { nhrpServerStatEntry 20 }

   nhrpServerStatRxErrInvalidExtension OBJECT-TYPE
       SYNTAX      Counter32
       MAX-ACCESS  read-only
       STATUS      current









       ::= { nhrpServerStatEntry 21 }

   nhrpServerStatRxErrInvalidResReplyReceived OBJECT-TYPE
       SYNTAX      Counter32
       MAX-ACCESS  read-only
       STATUS      current
       ::= { nhrpServerStatEntry 22 }

   nhrpServerStatRxErrAuthenticationFailure OBJECT-TYPE
       SYNTAX      Counter32
       MAX-ACCESS  read-only
       STATUS      current
       ::= { nhrpServerStatEntry 23 }





   nhrpServerStatRxErrHopCountExceeded OBJECT-TYPE
       SYNTAX      Counter32
       MAX-ACCESS  read-only
       STATUS      current
       ::= { nhrpServerStatEntry 24 }

   nhrpServerStatTxErrUnrecognizedExtension OBJECT-TYPE
       SYNTAX      Counter32
       MAX-ACCESS  read-only
       STATUS      current
       ::= { nhrpServerStatEntry 25 }


   nhrpServerStatTxErrLoopDetected OBJECT-TYPE
       SYNTAX      Counter32
       MAX-ACCESS  read-only
       STATUS      current
       ::= { nhrpServerStatEntry 26 }

   nhrpServerStatTxErrProtoAddrUnreachable OBJECT-TYPE
       SYNTAX      Counter32
       MAX-ACCESS  read-only
       STATUS      current
       ::= { nhrpServerStatEntry 27 }

   nhrpServerStatTxErrProtoError OBJECT-TYPE
       SYNTAX      Counter32
       MAX-ACCESS  read-only
       STATUS      current
       ::= { nhrpServerStatEntry 28 }









   nhrpServerStatTxErrSduSizeExceeded OBJECT-TYPE
       SYNTAX      Counter32
       MAX-ACCESS  read-only
       STATUS      current
       ::= { nhrpServerStatEntry 29 }

   nhrpServerStatTxErrInvalidExtension OBJECT-TYPE
       SYNTAX      Counter32
       MAX-ACCESS  read-only
       STATUS      current
       ::= { nhrpServerStatEntry 30 }

   nhrpServerStatTxErrAuthenticationFailure OBJECT-TYPE
       SYNTAX      Counter32
       MAX-ACCESS  read-only
       STATUS      current
       ::= { nhrpServerStatEntry 31 }

   nhrpServerStatTxErrHopCountExceeded OBJECT-TYPE
       SYNTAX      Counter32
       MAX-ACCESS  read-only
       STATUS      current
       ::= { nhrpServerStatEntry 32 }

   nhrpServerStatFwResolveReq OBJECT-TYPE
       SYNTAX      Counter32
       MAX-ACCESS  read-only
       STATUS      current
       ::= { nhrpServerStatEntry 33 }

   nhrpServerStatFwResolveReply OBJECT-TYPE
       SYNTAX      Counter32
       MAX-ACCESS  read-only
       STATUS      current







       ::= { nhrpServerStatEntry 34 }

   nhrpServerStatFwRegisterReq OBJECT-TYPE
       SYNTAX      Counter32
       MAX-ACCESS  read-only
       STATUS      current
       ::= { nhrpServerStatEntry 35 }

   nhrpServerStatFwRegisterReply OBJECT-TYPE
       SYNTAX      Counter32
       MAX-ACCESS  read-only
       STATUS      current
       ::= { nhrpServerStatEntry 36 }

   nhrpServerStatFwPurgeReq OBJECT-TYPE
       SYNTAX      Counter32
       MAX-ACCESS  read-only
       STATUS      current
       ::= { nhrpServerStatEntry 37 }

   nhrpServerStatFwPurgeReply OBJECT-TYPE
       SYNTAX      Counter32
       MAX-ACCESS  read-only
       STATUS      current
       ::= { nhrpServerStatEntry 38 }

   nhrpServerStatFwErrorIndication OBJECT-TYPE
       SYNTAX      Counter32
       MAX-ACCESS  read-only
       STATUS      current
       ::= { nhrpServerStatEntry 39 }

   nhrpServerStatDiscontinuityTime OBJECT-TYPE
       SYNTAX      TimeStamp
       MAX-ACCESS  read-only
       STATUS      current
       ::= { nhrpServerStatEntry 40 }


   nhrpConformance OBJECT IDENTIFIER ::= { nhrpMIB 2 }

   nhrpCompliances
       OBJECT IDENTIFIER ::= { nhrpConformance 1 }

   nhrpGroups
       OBJECT IDENTIFIER ::= { nhrpConformance 2 }

   nhrpModuleCompliance MODULE-COMPLIANCE
       STATUS current
       MODULE -- this module
           MANDATORY-GROUPS    { nhrpGeneralGroup }

           GROUP nhrpClientGroup

           GROUP nhrpServerGroup
       ::= { nhrpCompliances 1 }

   nhrpGeneralGroup OBJECT-GROUP
       OBJECTS {

           nhrpNextIndex,
           nhrpCachePrefixLength,
           nhrpCacheNextHopInternetworkAddr,
           nhrpCacheNbmaAddrType,
           nhrpCacheNbmaAddr,
           nhrpCacheNbmaSubaddr,
           nhrpCacheType,
           nhrpCacheState,





           nhrpCacheHoldingTimeValid,
           nhrpCacheHoldingTime,
           nhrpCacheNegotiatedMtu,
           nhrpCachePreference,
           nhrpCacheStorageType,
           nhrpCacheRowStatus,
           nhrpPurgeCacheIdentifier,
           nhrpPurgePrefixLength,
           nhrpPurgeRequestID,
           nhrpPurgeReplyExpected,
           nhrpPurgeRowStatus
       }
       STATUS    current
       ::= { nhrpGroups 1 }

   nhrpClientGroup OBJECT-GROUP
       OBJECTS {
           nhrpClientInternetworkAddrType,
           nhrpClientInternetworkAddr,
           nhrpClientNbmaAddrType,
           nhrpClientNbmaAddr,
           nhrpClientNbmaSubaddr,
           nhrpClientInitialRequestTimeout,
           nhrpClientRegistrationRequestRetries,
           nhrpClientResolutionRequestRetries,
           nhrpClientPurgeRequestRetries,
           nhrpClientDefaultMtu,
           nhrpClientHoldTime,
           nhrpClientRequestID,
           nhrpClientStorageType,
           nhrpClientRowStatus,
           nhrpClientRegUniqueness,
           nhrpClientRegState,
           nhrpClientRegRowStatus,
           nhrpClientNhsInternetworkAddrType,
           nhrpClientNhsInternetworkAddr,
           nhrpClientNhsNbmaAddrType,
           nhrpClientNhsNbmaAddr,
           nhrpClientNhsNbmaSubaddr,

           nhrpClientNhsInUse,
           nhrpClientNhsRowStatus,
           nhrpClientStatTxResolveReq,
           nhrpClientStatRxResolveReplyAck,
           nhrpClientStatRxResolveReplyNakProhibited,





           nhrpClientStatRxResolveReplyNakInsufResources,
           nhrpClientStatRxResolveReplyNakNoBinding,
           nhrpClientStatRxResolveReplyNakNotUnique,
           nhrpClientStatTxRegisterReq,
           nhrpClientStatRxRegisterAck,
           nhrpClientStatRxRegisterNakProhibited,
           nhrpClientStatRxRegisterNakInsufResources,
           nhrpClientStatRxRegisterNakAlreadyReg,
           nhrpClientStatRxPurgeReq,
           nhrpClientStatTxPurgeReq,
           nhrpClientStatRxPurgeReply,
           nhrpClientStatTxPurgeReply,
           nhrpClientStatTxErrorIndication,
           nhrpClientStatRxErrUnrecognizedExtension,
           nhrpClientStatRxErrLoopDetected,
           nhrpClientStatRxErrProtoAddrUnreachable,
           nhrpClientStatRxErrProtoError,
           nhrpClientStatRxErrSduSizeExceeded,
           nhrpClientStatRxErrInvalidExtension,
           nhrpClientStatRxErrAuthenticationFailure,
           nhrpClientStatRxErrHopCountExceeded,
           nhrpClientStatDiscontinuityTime
       }
       STATUS    current
       ::= { nhrpGroups 2 }

   nhrpServerGroup OBJECT-GROUP
       OBJECTS {
           nhrpServerInternetworkAddrType,
           nhrpServerInternetworkAddr,
           nhrpServerNbmaAddrType,
           nhrpServerNbmaAddr,
           nhrpServerNbmaSubaddr,
           nhrpServerStorageType,
           nhrpServerRowStatus,
           nhrpServerCacheAuthoritative,
           nhrpServerCacheUniqueness,
           nhrpServerNhcPrefixLength,
           nhrpServerNhcInternetworkAddrType,
           nhrpServerNhcInternetworkAddr,
           nhrpServerNhcNbmaAddrType,
           nhrpServerNhcNbmaAddr,
           nhrpServerNhcNbmaSubaddr,
           nhrpServerNhcInUse,
           nhrpServerNhcRowStatus,
           nhrpServerStatRxResolveReq,





           nhrpServerStatTxResolveReplyAck,
           nhrpServerStatTxResolveReplyNakProhibited,
           nhrpServerStatTxResolveReplyNakInsufResources,
           nhrpServerStatTxResolveReplyNakNoBinding,
           nhrpServerStatTxResolveReplyNakNotUnique,
           nhrpServerStatRxRegisterReq,
           nhrpServerStatTxRegisterAck,
           nhrpServerStatTxRegisterNakProhibited,
           nhrpServerStatTxRegisterNakInsufResources,
           nhrpServerStatTxRegisterNakAlreadyReg,
           nhrpServerStatRxPurgeReq,
           nhrpServerStatTxPurgeReq,
           nhrpServerStatRxPurgeReply,
           nhrpServerStatTxPurgeReply,
           nhrpServerStatRxErrUnrecognizedExtension,
           nhrpServerStatRxErrLoopDetected,
           nhrpServerStatRxErrProtoAddrUnreachable,
           nhrpServerStatRxErrProtoError,
           nhrpServerStatRxErrSduSizeExceeded,
           nhrpServerStatRxErrInvalidExtension,
           nhrpServerStatRxErrInvalidResReplyReceived,
           nhrpServerStatRxErrAuthenticationFailure,
           nhrpServerStatRxErrHopCountExceeded,
           nhrpServerStatTxErrUnrecognizedExtension,
           nhrpServerStatTxErrLoopDetected,
           nhrpServerStatTxErrProtoAddrUnreachable,
           nhrpServerStatTxErrProtoError,
           nhrpServerStatTxErrSduSizeExceeded,
           nhrpServerStatTxErrInvalidExtension,
           nhrpServerStatTxErrAuthenticationFailure,
           nhrpServerStatTxErrHopCountExceeded,
           nhrpServerStatFwResolveReq,
           nhrpServerStatFwResolveReply,
           nhrpServerStatFwRegisterReq,
           nhrpServerStatFwRegisterReply,
           nhrpServerStatFwPurgeReq,
           nhrpServerStatFwPurgeReply,
           nhrpServerStatFwErrorIndication,
           nhrpServerStatDiscontinuityTime
       }
       STATUS    current
       ::= { nhrpGroups 3 }

   END
