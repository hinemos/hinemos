ITU-ALARM-MIB DEFINITIONS ::= BEGIN

   IMPORTS
      MODULE-IDENTITY, OBJECT-TYPE,
      Gauge32, mib-2
          FROM SNMPv2-SMI                -- [RFC2578]
      AutonomousType, RowPointer
          FROM SNMPv2-TC                 -- [RFC2579]
      SnmpAdminString
          FROM SNMP-FRAMEWORK-MIB        -- [RFC3411]
      alarmListName, alarmModelIndex,
      alarmActiveDateAndTime, alarmActiveIndex
          FROM ALARM-MIB                 -- [RFC3877]
      ItuPerceivedSeverity,
      ItuTrendIndication
          FROM ITU-ALARM-TC-MIB          -- [RFC3877]
      IANAItuProbableCause,
      IANAItuEventType
          FROM IANA-ITU-ALARM-TC-MIB     -- [RFC3877]
      MODULE-COMPLIANCE, OBJECT-GROUP
          FROM SNMPv2-CONF               -- [RFC2580]
      ZeroBasedCounter32
          FROM RMON2-MIB;                -- [RFC2021]

     ituAlarmMIB MODULE-IDENTITY
         LAST-UPDATED "200409090000Z"  -- September 09, 2004
         ORGANIZATION "IETF Distributed Management Working Group"
         ::= { mib-2 121 }

   ituAlarmObjects OBJECT IDENTIFIER ::= { ituAlarmMIB 1 }

   ituAlarmModel OBJECT IDENTIFIER ::= { ituAlarmObjects 1 }

   ituAlarmActive  OBJECT IDENTIFIER ::= { ituAlarmObjects 2 }

   ituAlarmTable OBJECT-TYPE
      SYNTAX      SEQUENCE OF ItuAlarmEntry
      MAX-ACCESS  not-accessible
      STATUS      current
      ::= { ituAlarmModel 1 }

   ituAlarmEntry OBJECT-TYPE
      SYNTAX      ItuAlarmEntry
      MAX-ACCESS  not-accessible
      STATUS      current
      INDEX       { alarmListName, alarmModelIndex,
                   ituAlarmPerceivedSeverity }
      ::= { ituAlarmTable 1 }

   ItuAlarmEntry ::= SEQUENCE {
      ituAlarmPerceivedSeverity     ItuPerceivedSeverity,
      ituAlarmEventType             IANAItuEventType,
      ituAlarmProbableCause         IANAItuProbableCause,
      ituAlarmAdditionalText        SnmpAdminString,
      ituAlarmGenericModel          RowPointer }

   ituAlarmPerceivedSeverity OBJECT-TYPE
      SYNTAX  ItuPerceivedSeverity
      MAX-ACCESS   not-accessible
      STATUS       current
       ::= { ituAlarmEntry 1 }

   ituAlarmEventType OBJECT-TYPE
      SYNTAX       IANAItuEventType
      MAX-ACCESS   read-write
      STATUS       current
       ::= { ituAlarmEntry 2 }

   ituAlarmProbableCause OBJECT-TYPE
      SYNTAX      IANAItuProbableCause
      MAX-ACCESS  read-write
      STATUS       current
       ::= { ituAlarmEntry 3 }

   ituAlarmAdditionalText OBJECT-TYPE
      SYNTAX  SnmpAdminString
      MAX-ACCESS read-write
      STATUS     current
       ::= { ituAlarmEntry 4}

   ituAlarmGenericModel OBJECT-TYPE
      SYNTAX     RowPointer
      MAX-ACCESS read-write
      STATUS     current
      ::= { ituAlarmEntry 5 }


   ituAlarmActiveTable OBJECT-TYPE
      SYNTAX      SEQUENCE OF ItuAlarmActiveEntry
      MAX-ACCESS  not-accessible
      STATUS      current
      ::= { ituAlarmActive 1 }

   ituAlarmActiveEntry OBJECT-TYPE
      SYNTAX      ItuAlarmActiveEntry
      MAX-ACCESS  not-accessible
      STATUS      current
      INDEX       { alarmListName, alarmActiveDateAndTime,
                   alarmActiveIndex }
      ::= { ituAlarmActiveTable 1 }

   ItuAlarmActiveEntry ::= SEQUENCE {
       ituAlarmActiveTrendIndication       ItuTrendIndication,
       ituAlarmActiveDetector              AutonomousType,
       ituAlarmActiveServiceProvider       AutonomousType,
       ituAlarmActiveServiceUser           AutonomousType
       }

   ituAlarmActiveTrendIndication OBJECT-TYPE
      SYNTAX      ItuTrendIndication
      MAX-ACCESS  read-only
      STATUS       current
       ::= { ituAlarmActiveEntry 1 }






   ituAlarmActiveDetector OBJECT-TYPE
      SYNTAX AutonomousType
      MAX-ACCESS read-only
      STATUS current
      ::= { ituAlarmActiveEntry 2 }

   ituAlarmActiveServiceProvider OBJECT-TYPE
      SYNTAX AutonomousType
      MAX-ACCESS read-only
      STATUS current
      ::= { ituAlarmActiveEntry 3 }

   ituAlarmActiveServiceUser OBJECT-TYPE
      SYNTAX AutonomousType
      MAX-ACCESS read-only
      STATUS current
      ::= { ituAlarmActiveEntry 4 }


   ituAlarmActiveStatsTable  OBJECT-TYPE
         SYNTAX  SEQUENCE OF ItuAlarmActiveStatsEntry
         MAX-ACCESS  not-accessible
         STATUS  current
     ::= { ituAlarmActive 2 }







   ituAlarmActiveStatsEntry OBJECT-TYPE
         SYNTAX  ItuAlarmActiveStatsEntry
         MAX-ACCESS  not-accessible
         STATUS  current
         INDEX   { alarmListName }

     ::= {  ituAlarmActiveStatsTable 1 }

   ItuAlarmActiveStatsEntry ::=
    SEQUENCE {
      ituAlarmActiveStatsIndeterminateCurrent Gauge32,
      ituAlarmActiveStatsCriticalCurrent      Gauge32,
      ituAlarmActiveStatsMajorCurrent         Gauge32,
      ituAlarmActiveStatsMinorCurrent         Gauge32,
      ituAlarmActiveStatsWarningCurrent       Gauge32,
      ituAlarmActiveStatsIndeterminates       ZeroBasedCounter32,
      ituAlarmActiveStatsCriticals            ZeroBasedCounter32,
      ituAlarmActiveStatsMajors               ZeroBasedCounter32,
      ituAlarmActiveStatsMinors               ZeroBasedCounter32,
      ituAlarmActiveStatsWarnings             ZeroBasedCounter32
    }

   ituAlarmActiveStatsIndeterminateCurrent OBJECT-TYPE
      SYNTAX      Gauge32
      MAX-ACCESS  read-only
      STATUS      current
      ::= { ituAlarmActiveStatsEntry 1 }

   ituAlarmActiveStatsCriticalCurrent OBJECT-TYPE
      SYNTAX      Gauge32
      MAX-ACCESS  read-only
      STATUS      current
      ::= { ituAlarmActiveStatsEntry 2 }

   ituAlarmActiveStatsMajorCurrent OBJECT-TYPE
      SYNTAX      Gauge32
      MAX-ACCESS  read-only
      STATUS      current
      ::= { ituAlarmActiveStatsEntry 3 }

   ituAlarmActiveStatsMinorCurrent OBJECT-TYPE
      SYNTAX      Gauge32
      MAX-ACCESS  read-only
      STATUS      current
      ::= { ituAlarmActiveStatsEntry 4 }

   ituAlarmActiveStatsWarningCurrent OBJECT-TYPE
      SYNTAX      Gauge32
      MAX-ACCESS  read-only
      STATUS      current
      ::= { ituAlarmActiveStatsEntry 5 }

   ituAlarmActiveStatsIndeterminates OBJECT-TYPE
      SYNTAX      ZeroBasedCounter32
      MAX-ACCESS  read-only
      STATUS      current
      ::= { ituAlarmActiveStatsEntry 6 }

   ituAlarmActiveStatsCriticals OBJECT-TYPE
      SYNTAX      ZeroBasedCounter32
      MAX-ACCESS  read-only
      STATUS      current
      ::= { ituAlarmActiveStatsEntry 7 }

   ituAlarmActiveStatsMajors OBJECT-TYPE
      SYNTAX      ZeroBasedCounter32
      MAX-ACCESS  read-only
      STATUS      current
      ::= { ituAlarmActiveStatsEntry 8 }





   ituAlarmActiveStatsMinors OBJECT-TYPE
      SYNTAX      ZeroBasedCounter32
      MAX-ACCESS  read-only
      STATUS      current
      ::= { ituAlarmActiveStatsEntry 9 }

   ituAlarmActiveStatsWarnings OBJECT-TYPE
      SYNTAX      ZeroBasedCounter32
      MAX-ACCESS  read-only
      STATUS      current
      ::= { ituAlarmActiveStatsEntry 10 }


   ituAlarmConformance OBJECT IDENTIFIER ::= { ituAlarmMIB 2 }
   ituAlarmCompliances  OBJECT IDENTIFIER ::= { ituAlarmConformance 1 }

   ituAlarmCompliance MODULE-COMPLIANCE
      STATUS  current
      MODULE -- this module
          MANDATORY-GROUPS {
              ituAlarmGroup
              }
      GROUP       ituAlarmServiceUserGroup
      GROUP       ituAlarmSecurityGroup
      GROUP       ituAlarmStatisticsGroup
     ::= { ituAlarmCompliances 1 }

   ituAlarmGroups OBJECT IDENTIFIER ::= { ituAlarmConformance 2 }

   ituAlarmGroup OBJECT-GROUP
    OBJECTS {
              ituAlarmEventType,





              ituAlarmProbableCause,
              ituAlarmGenericModel
            }
    STATUS   current
    ::= { ituAlarmGroups 1}

   ituAlarmServiceUserGroup OBJECT-GROUP
    OBJECTS {
              ituAlarmAdditionalText,
              ituAlarmActiveTrendIndication
            }
    STATUS current
    ::= { ituAlarmGroups 2 }

   ituAlarmSecurityGroup OBJECT-GROUP
     OBJECTS {
             ituAlarmActiveDetector,
             ituAlarmActiveServiceProvider,
             ituAlarmActiveServiceUser
            }
     STATUS current
     ::= { ituAlarmGroups 3 }

   ituAlarmStatisticsGroup OBJECT-GROUP
     OBJECTS {
            ituAlarmActiveStatsIndeterminateCurrent,
            ituAlarmActiveStatsCriticalCurrent,
            ituAlarmActiveStatsMajorCurrent,
            ituAlarmActiveStatsMinorCurrent,
            ituAlarmActiveStatsWarningCurrent,
            ituAlarmActiveStatsIndeterminates,
            ituAlarmActiveStatsCriticals,
            ituAlarmActiveStatsMajors,
            ituAlarmActiveStatsMinors,
            ituAlarmActiveStatsWarnings
             }
     STATUS current
     ::= { ituAlarmGroups 4 }

   END
