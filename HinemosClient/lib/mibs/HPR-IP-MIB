HPR-IP-MIB DEFINITIONS ::= BEGIN

IMPORTS
        MODULE-IDENTITY,OBJECT-TYPE, Counter32
                    FROM SNMPv2-SMI
        DisplayString, RowStatus, TEXTUAL-CONVENTION
                    FROM SNMPv2-TC
        MODULE-COMPLIANCE, OBJECT-GROUP
                    FROM SNMPv2-CONF
        SnaControlPointName
                    FROM APPN-MIB
        hprObjects, hprCompliances, hprGroups
                    FROM HPR-MIB  ;

hprIp   MODULE-IDENTITY
   LAST-UPDATED "9809240000Z" -- September 24, 1998
   ORGANIZATION "IETF SNA NAU MIB WG / AIW APPN MIBs SIG"

   ::= { hprObjects 5 }

AppnTrafficType ::= TEXTUAL-CONVENTION
      STATUS current

      SYNTAX INTEGER { low (1),
                       medium (2),
                       high (3),
                       network (4),
                       llcAndFnRoutedNlp (5) }

AppnTOSPrecedence ::= TEXTUAL-CONVENTION
      STATUS current

      SYNTAX DisplayString (SIZE(3))







hprIpActiveLsTable OBJECT-TYPE
      SYNTAX SEQUENCE OF HprIpActiveLsEntry
      MAX-ACCESS not-accessible
      STATUS current

      ::= { hprIp 1 }

hprIpActiveLsEntry OBJECT-TYPE
      SYNTAX HprIpActiveLsEntry
      MAX-ACCESS not-accessible
      STATUS current

      INDEX { hprIpActiveLsLsName,
              hprIpActiveLsAppnTrafficType }

      ::= { hprIpActiveLsTable 1 }

HprIpActiveLsEntry ::= SEQUENCE {
        hprIpActiveLsLsName              DisplayString,
        hprIpActiveLsAppnTrafficType     AppnTrafficType,
        hprIpActiveLsUdpPackets          Counter32 }

hprIpActiveLsLsName OBJECT-TYPE
      SYNTAX DisplayString (SIZE (1..10))
      MAX-ACCESS not-accessible
      STATUS current






      ::= { hprIpActiveLsEntry 1 }

hprIpActiveLsAppnTrafficType OBJECT-TYPE
      SYNTAX AppnTrafficType
      MAX-ACCESS not-accessible
      STATUS current

      ::= { hprIpActiveLsEntry 2 }

hprIpActiveLsUdpPackets OBJECT-TYPE
      SYNTAX Counter32
      MAX-ACCESS read-only
      STATUS current

      ::= { hprIpActiveLsEntry 3 }



hprIpAppnPortTable OBJECT-TYPE
      SYNTAX SEQUENCE OF HprIpAppnPortEntry
      MAX-ACCESS not-accessible
      STATUS current

      ::= { hprIp 2 }





hprIpAppnPortEntry OBJECT-TYPE
      SYNTAX HprIpAppnPortEntry
      MAX-ACCESS not-accessible
      STATUS current

      INDEX { hprIpAppnPortName,
              hprIpAppnPortAppnTrafficType }

      ::= { hprIpAppnPortTable 1 }

HprIpAppnPortEntry ::= SEQUENCE {
        hprIpAppnPortName            DisplayString,
        hprIpAppnPortAppnTrafficType AppnTrafficType,
        hprIpAppnPortTOSPrecedence   AppnTOSPrecedence }

hprIpAppnPortName OBJECT-TYPE
      SYNTAX DisplayString (SIZE (1..10))
      MAX-ACCESS not-accessible
      STATUS current

      ::= { hprIpAppnPortEntry 1 }

hprIpAppnPortAppnTrafficType OBJECT-TYPE
      SYNTAX AppnTrafficType
      MAX-ACCESS not-accessible
      STATUS current

      ::= { hprIpAppnPortEntry 2 }

hprIpAppnPortTOSPrecedence OBJECT-TYPE
      SYNTAX AppnTOSPrecedence
      MAX-ACCESS read-write
      STATUS current

      ::= { hprIpAppnPortEntry 3 }


hprIpLsTable OBJECT-TYPE
      SYNTAX SEQUENCE OF HprIpLsEntry
      MAX-ACCESS not-accessible
      STATUS current

      ::= { hprIp 3 }

hprIpLsEntry OBJECT-TYPE
      SYNTAX HprIpLsEntry
      MAX-ACCESS not-accessible
      STATUS current

      INDEX { hprIpLsLsName,
              hprIpLsAppnTrafficType }

      ::= { hprIpLsTable 1 }

HprIpLsEntry ::= SEQUENCE {
        hprIpLsLsName            DisplayString,
        hprIpLsAppnTrafficType   AppnTrafficType,
        hprIpLsTOSPrecedence     AppnTOSPrecedence,
        hprIpLsRowStatus         RowStatus }

hprIpLsLsName OBJECT-TYPE
      SYNTAX DisplayString (SIZE (1..10))
      MAX-ACCESS not-accessible
      STATUS current






      ::= { hprIpLsEntry 1 }

hprIpLsAppnTrafficType OBJECT-TYPE
      SYNTAX AppnTrafficType
      MAX-ACCESS not-accessible
      STATUS current

      ::= { hprIpLsEntry 2 }

hprIpLsTOSPrecedence OBJECT-TYPE
      SYNTAX AppnTOSPrecedence
      MAX-ACCESS read-create
      STATUS current

      ::= { hprIpLsEntry 3 }

hprIpLsRowStatus OBJECT-TYPE
      SYNTAX RowStatus
      MAX-ACCESS read-create
      STATUS current

      ::= { hprIpLsEntry 4 }







hprIpCnTable OBJECT-TYPE
      SYNTAX SEQUENCE OF HprIpCnEntry
      MAX-ACCESS not-accessible
      STATUS current

      ::= { hprIp 4 }

hprIpCnEntry OBJECT-TYPE
      SYNTAX HprIpCnEntry
      MAX-ACCESS not-accessible
      STATUS current

      INDEX { hprIpCnVrnName,
              hprIpCnAppnTrafficType }

      ::= { hprIpCnTable 1 }

HprIpCnEntry ::= SEQUENCE {
        hprIpCnVrnName           SnaControlPointName,
        hprIpCnAppnTrafficType   AppnTrafficType,
        hprIpCnTOSPrecedence     AppnTOSPrecedence,
        hprIpCnRowStatus         RowStatus }

hprIpCnVrnName OBJECT-TYPE
      SYNTAX SnaControlPointName
      MAX-ACCESS not-accessible
      STATUS current

      ::= { hprIpCnEntry 1 }

hprIpCnAppnTrafficType OBJECT-TYPE
      SYNTAX AppnTrafficType
      MAX-ACCESS not-accessible
      STATUS current

      ::= { hprIpCnEntry 2 }

hprIpCnTOSPrecedence OBJECT-TYPE
      SYNTAX AppnTOSPrecedence
      MAX-ACCESS read-create
      STATUS current
      ::= { hprIpCnEntry 3 }

hprIpCnRowStatus OBJECT-TYPE
      SYNTAX RowStatus
      MAX-ACCESS read-create
      STATUS current

      ::= { hprIpCnEntry 4 }



hprIpCompliance MODULE-COMPLIANCE
       STATUS current
   MODULE   -- this module

   GROUP hprIpMonitoringGroup

   GROUP hprIpConfigurationGroup

   OBJECT hprIpAppnPortTOSPrecedence
   MIN-ACCESS  read-only

   OBJECT hprIpLsTOSPrecedence
   MIN-ACCESS  read-only

   OBJECT hprIpLsRowStatus
   MIN-ACCESS  read-only






   OBJECT hprIpCnTOSPrecedence
   MIN-ACCESS  read-only

   OBJECT hprIpCnRowStatus
   MIN-ACCESS  read-only

::= { hprCompliances 2 }


hprIpMonitoringGroup OBJECT-GROUP
      OBJECTS { hprIpActiveLsUdpPackets }
      STATUS current

::= { hprGroups 5 }

hprIpConfigurationGroup OBJECT-GROUP
      OBJECTS { hprIpAppnPortTOSPrecedence,
                hprIpLsTOSPrecedence,
                hprIpLsRowStatus,
                hprIpCnTOSPrecedence,
                hprIpCnRowStatus }
      STATUS current

::= { hprGroups 6 }

END
