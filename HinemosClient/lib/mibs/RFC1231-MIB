RFC1231-MIB DEFINITIONS ::= BEGIN


          IMPORTS
                  experimental
                          FROM RFC1155-SMI
                  OBJECT-TYPE
                          FROM RFC-1212;




          dot5    OBJECT IDENTIFIER ::= { experimental 4 }


          MacAddress ::= OCTET STRING (SIZE (6))    -- a 6 octet









          dot5Table  OBJECT-TYPE
                     SYNTAX  SEQUENCE OF Dot5Entry
                     ACCESS  not-accessible
                     STATUS  mandatory
                     ::= { dot5 1 }

          dot5Entry  OBJECT-TYPE
                     SYNTAX  Dot5Entry
                     ACCESS  not-accessible
                     STATUS  mandatory
                     INDEX   { dot5IfIndex }
                     ::= { dot5Table 1 }

          Dot5Entry
              ::= SEQUENCE {
                      dot5IfIndex
                          INTEGER,
                      dot5Commands
                          INTEGER,
                      dot5RingStatus
                          INTEGER,
                      dot5RingState
                          INTEGER,
                      dot5RingOpenStatus
                          INTEGER,
                      dot5RingSpeed
                          INTEGER,
                      dot5UpStream
                          MacAddress,
                      dot5ActMonParticipate
                          INTEGER,
                      dot5Functional
                          MacAddress
                  }

          dot5IfIndex  OBJECT-TYPE
                     SYNTAX  INTEGER
                     ACCESS  read-only
                     STATUS  mandatory
                     ::= { dot5Entry 1 }

          dot5Commands  OBJECT-TYPE
                     SYNTAX  INTEGER {
                                   no-op(1),
                                   open(2),
                                   reset(3),
                                   close(4)
                             }
                     ACCESS  read-write
                     STATUS  mandatory
                     ::= { dot5Entry 2 }

          dot5RingStatus OBJECT-TYPE
                     SYNTAX  INTEGER
                     ACCESS  read-only
                     STATUS  mandatory
                     ::= { dot5Entry 3 }

          dot5RingState  OBJECT-TYPE
                     SYNTAX  INTEGER {
                                   opened(1),
                                   closed(2),
                                   opening(3),
                                   closing(4),
                                   openFailure(5),
                                   ringFailure(6)
                             }
                     ACCESS  read-only
                     STATUS  mandatory
                     ::= { dot5Entry 4 }

          dot5RingOpenStatus  OBJECT-TYPE
                     SYNTAX  INTEGER {
                                   noOpen(1),     -- no open attempted
                                   badParam(2),
                                   lobeFailed(3),





                                   signalLoss(4),
                                   insertionTimeout(5),
                                   ringFailed(6),
                                   beaconing(7),
                                   duplicateMAC(8),
                                   requestFailed(9),
                                   removeReceived(10),
                                   open(11)      -- last open successful
                             }
                     ACCESS  read-only
                     STATUS  mandatory
                     ::= { dot5Entry 5 }

          dot5RingSpeed  OBJECT-TYPE
                     SYNTAX  INTEGER {
                                   unknown(1),
                                   oneMegabit(2),
                                   fourMegabit(3),
                                   sixteenMegabit(4)
                             }
                     ACCESS  read-write
                     STATUS  mandatory
                     ::= { dot5Entry 6 }

          dot5UpStream  OBJECT-TYPE
                     SYNTAX  MacAddress
                     ACCESS  read-only
                     STATUS  mandatory
                     ::= { dot5Entry 7 }

          dot5ActMonParticipate OBJECT-TYPE
                     SYNTAX  INTEGER {
                                   true(1),
                                   false(2)
                             }
                     ACCESS  read-write
                     STATUS  mandatory
                     ::= { dot5Entry 8 }

          dot5Functional OBJECT-TYPE
                     SYNTAX  MacAddress
                     ACCESS  read-write
                     STATUS  mandatory
                     ::= { dot5Entry 9 }





          dot5StatsTable  OBJECT-TYPE
                     SYNTAX  SEQUENCE OF Dot5StatsEntry
                     ACCESS  not-accessible
                     STATUS  mandatory
                     ::= { dot5 2 }

          dot5StatsEntry  OBJECT-TYPE
                     SYNTAX  Dot5StatsEntry
                     ACCESS  not-accessible
                     STATUS  mandatory
                     INDEX   { dot5StatsIfIndex }
                     ::= { dot5StatsTable 1 }

          Dot5StatsEntry
              ::= SEQUENCE {
                      dot5StatsIfIndex
                          INTEGER,
                      dot5StatsLineErrors
                          Counter,
                      dot5StatsBurstErrors
                          Counter,
                      dot5StatsACErrors
                          Counter,
                      dot5StatsAbortTransErrors
                          Counter,
                      dot5StatsInternalErrors
                          Counter,
                      dot5StatsLostFrameErrors
                          Counter,
                      dot5StatsReceiveCongestions
                          Counter,
                      dot5StatsFrameCopiedErrors
                          Counter,
                      dot5StatsTokenErrors
                          Counter,
                      dot5StatsSoftErrors
                          Counter,
                      dot5StatsHardErrors
                          Counter,
                      dot5StatsSignalLoss
                          Counter,
                      dot5StatsTransmitBeacons
                          Counter,
                      dot5StatsRecoverys
                          Counter,
                      dot5StatsLobeWires
                          Counter,
                      dot5StatsRemoves
                          Counter,
                      dot5StatsSingles
                          Counter,
                      dot5StatsFreqErrors
                          Counter
                  }







          dot5StatsIfIndex  OBJECT-TYPE
                     SYNTAX  INTEGER
                     ACCESS  read-only
                     STATUS  mandatory
                     ::= { dot5StatsEntry 1 }

          dot5StatsLineErrors OBJECT-TYPE
                     SYNTAX  Counter
                     ACCESS  read-only
                     STATUS  mandatory
                     ::= { dot5StatsEntry 2 }

          dot5StatsBurstErrors OBJECT-TYPE
                     SYNTAX  Counter
                     ACCESS  read-only
                     STATUS  mandatory
                     ::= { dot5StatsEntry 3 }

          dot5StatsACErrors OBJECT-TYPE
                     SYNTAX  Counter
                     ACCESS  read-only
                     STATUS  mandatory
                     ::= { dot5StatsEntry 4 }

          dot5StatsAbortTransErrors OBJECT-TYPE
                     SYNTAX  Counter
                     ACCESS  read-only
                     STATUS  mandatory
                     ::= { dot5StatsEntry 5 }

          dot5StatsInternalErrors OBJECT-TYPE
                     SYNTAX  Counter
                     ACCESS  read-only
                     STATUS  mandatory
                     ::= { dot5StatsEntry 6 }

          dot5StatsLostFrameErrors OBJECT-TYPE
                     SYNTAX  Counter
                     ACCESS  read-only
                     STATUS  mandatory
                     ::= { dot5StatsEntry 7 }

          dot5StatsReceiveCongestions OBJECT-TYPE
                     SYNTAX  Counter
                     ACCESS  read-only
                     STATUS  mandatory
                     ::= { dot5StatsEntry 8 }





          dot5StatsFrameCopiedErrors OBJECT-TYPE
                     SYNTAX  Counter
                     ACCESS  read-only
                     STATUS  mandatory
                     ::= { dot5StatsEntry 9 }

          dot5StatsTokenErrors OBJECT-TYPE
                     SYNTAX  Counter
                     ACCESS  read-only
                     STATUS  mandatory
                     ::= { dot5StatsEntry 10 }

          dot5StatsSoftErrors OBJECT-TYPE
                     SYNTAX  Counter
                     ACCESS  read-only
                     STATUS  mandatory
                     ::= { dot5StatsEntry 11 }

          dot5StatsHardErrors OBJECT-TYPE
                     SYNTAX  Counter
                     ACCESS  read-only
                     STATUS  mandatory
                     ::= { dot5StatsEntry 12 }





          dot5StatsSignalLoss OBJECT-TYPE
                     SYNTAX  Counter
                     ACCESS  read-only
                     STATUS  mandatory
                     ::= { dot5StatsEntry 13 }

          dot5StatsTransmitBeacons OBJECT-TYPE
                     SYNTAX  Counter
                     ACCESS  read-only
                     STATUS  mandatory
                     ::= { dot5StatsEntry 14 }

          dot5StatsRecoverys OBJECT-TYPE
                     SYNTAX  Counter
                     ACCESS  read-only
                     STATUS  mandatory
                     ::= { dot5StatsEntry 15 }

          dot5StatsLobeWires OBJECT-TYPE
                     SYNTAX  Counter
                     ACCESS  read-only
                     STATUS  mandatory
                     ::= { dot5StatsEntry 16 }

          dot5StatsRemoves OBJECT-TYPE
                     SYNTAX  Counter
                     ACCESS  read-only
                     STATUS  mandatory





                     ::= { dot5StatsEntry 17 }

          dot5StatsSingles OBJECT-TYPE
                     SYNTAX  Counter
                     ACCESS  read-only
                     STATUS  mandatory
                     ::= { dot5StatsEntry 18 }

          dot5StatsFreqErrors OBJECT-TYPE
                     SYNTAX  Counter
                     ACCESS  read-only
                     STATUS  optional
                     ::= { dot5StatsEntry 19 }




          dot5TimerTable  OBJECT-TYPE
                     SYNTAX  SEQUENCE OF Dot5TimerEntry
                     ACCESS  not-accessible
                     STATUS  mandatory
                     ::= { dot5 5 }

          dot5TimerEntry  OBJECT-TYPE
                     SYNTAX  Dot5TimerEntry
                     ACCESS  not-accessible
                     STATUS  mandatory
                     INDEX   { dot5TimerIfIndex }
                     ::= { dot5TimerTable 1 }

          Dot5TimerEntry
              ::= SEQUENCE {
                     dot5TimerIfIndex
                         INTEGER,
                     dot5TimerReturnRepeat
                         INTEGER,
                     dot5TimerHolding
                         INTEGER,
                     dot5TimerQueuePDU
                         INTEGER,
                     dot5TimerValidTransmit
                         INTEGER,
                     dot5TimerNoToken
                         INTEGER,
                     dot5TimerActiveMon
                         INTEGER,
                     dot5TimerStandbyMon
                         INTEGER,
                     dot5TimerErrorReport
                         INTEGER,
                     dot5TimerBeaconTransmit
                         INTEGER,
                     dot5TimerBeaconReceive
                         INTEGER
                 }

          dot5TimerIfIndex  OBJECT-TYPE
                     SYNTAX  INTEGER
                     ACCESS  read-only
                     STATUS  mandatory
                     ::= { dot5TimerEntry 1 }

          dot5TimerReturnRepeat  OBJECT-TYPE
                     SYNTAX  INTEGER
                     ACCESS  read-only
                     STATUS  mandatory
                     ::= { dot5TimerEntry 2 }

          dot5TimerHolding  OBJECT-TYPE
                     SYNTAX  INTEGER
                     ACCESS  read-only
                     STATUS  mandatory
                     ::= { dot5TimerEntry 3 }

          dot5TimerQueuePDU  OBJECT-TYPE
                     SYNTAX  INTEGER
                     ACCESS  read-only
                     STATUS  mandatory
                     ::= { dot5TimerEntry 4 }

          dot5TimerValidTransmit OBJECT-TYPE
                     SYNTAX  INTEGER
                     ACCESS  read-only
                     STATUS  mandatory
                     ::= { dot5TimerEntry 5 }

          dot5TimerNoToken  OBJECT-TYPE
                     SYNTAX  INTEGER
                     ACCESS  read-only
                     STATUS  mandatory
                     ::= { dot5TimerEntry 6 }

          dot5TimerActiveMon  OBJECT-TYPE
                     SYNTAX  INTEGER
                     ACCESS  read-only
                     STATUS  mandatory
                     ::= { dot5TimerEntry 7 }

          dot5TimerStandbyMon  OBJECT-TYPE
                     SYNTAX  INTEGER
                     ACCESS  read-only
                     STATUS  mandatory
                     ::= { dot5TimerEntry 8 }

          dot5TimerErrorReport  OBJECT-TYPE
                     SYNTAX  INTEGER
                     ACCESS  read-only
                     STATUS  mandatory
                     ::= { dot5TimerEntry 9 }

          dot5TimerBeaconTransmit  OBJECT-TYPE
                     SYNTAX  INTEGER
                     ACCESS  read-only
                     STATUS  mandatory
                     ::= { dot5TimerEntry 10 }

          dot5TimerBeaconReceive  OBJECT-TYPE
                     SYNTAX  INTEGER
                     ACCESS  read-only
                     STATUS  mandatory
                     ::= { dot5TimerEntry 11 }



          dot5Tests         OBJECT IDENTIFIER ::= { dot5 3 }







          testInsertFunc    OBJECT IDENTIFIER ::= { dot5Tests 1 }



          dot5ChipSets   OBJECT IDENTIFIER ::= { dot5 4 }


          chipSetIBM16       OBJECT IDENTIFIER ::= { dot5ChipSets 1 }

          chipSetTItms380    OBJECT IDENTIFIER ::= { dot5ChipSets 2 }

          chipSetTItms380c16 OBJECT IDENTIFIER ::= { dot5ChipSets 3 }

          END
