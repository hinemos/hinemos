RFC1407-MIB DEFINITIONS ::= BEGIN

               IMPORTS
                       Gauge
                               FROM RFC1155-SMI
                       DisplayString, transmission
                               FROM RFC1213-MIB
                       OBJECT-TYPE
                               FROM RFC-1212;


                       ds3  OBJECT IDENTIFIER ::= { transmission 30 }






               dsx3ConfigTable OBJECT-TYPE
                   SYNTAX  SEQUENCE OF Dsx3ConfigEntry
                   ACCESS  not-accessible
                   STATUS  mandatory
                  ::= { ds3 5 }

              dsx3ConfigEntry OBJECT-TYPE
                  SYNTAX  Dsx3ConfigEntry
                  ACCESS  not-accessible
                  STATUS  mandatory
                 INDEX   { dsx3LineIndex }
                 ::= { dsx3ConfigTable 1 }






             Dsx3ConfigEntry ::=
                 SEQUENCE {
                     dsx3LineIndex
                         INTEGER,
                     dsx3IfIndex
                         INTEGER,
                     dsx3TimeElapsed
                         INTEGER,
                     dsx3ValidIntervals
                         INTEGER,
                     dsx3LineType
                         INTEGER,
                     dsx3LineCoding
                         INTEGER,
                     dsx3SendCode
                         INTEGER,
                     dsx3CircuitIdentifier
                         DisplayString,
                     dsx3LoopbackConfig
                         INTEGER,
                     dsx3LineStatus
                         INTEGER,
                     dsx3TransmitClockSource
                         INTEGER
             }

             dsx3LineIndex OBJECT-TYPE
                 SYNTAX  INTEGER (1..65535)
                 ACCESS  read-only
                 STATUS  mandatory
                ::= { dsx3ConfigEntry 1 }

            dsx3IfIndex OBJECT-TYPE
                SYNTAX  INTEGER (1..65535)
                ACCESS  read-only
                STATUS  mandatory





               ::= { dsx3ConfigEntry 2 }

           dsx3TimeElapsed OBJECT-TYPE
               SYNTAX  INTEGER (0..899)
               ACCESS  read-only
               STATUS  mandatory
              ::= { dsx3ConfigEntry 3 }

          dsx3ValidIntervals OBJECT-TYPE
              SYNTAX  INTEGER (0..96)
              ACCESS  read-only
              STATUS  mandatory
              ::= { dsx3ConfigEntry 4 }

          dsx3LineType OBJECT-TYPE
              SYNTAX  INTEGER {
                          dsx3other(1),
                          dsx3M23(2),
                          dsx3SYNTRAN(3),
                          dsx3CbitParity(4),
                          dsx3ClearChannel(5),
                          e3other(6),
                          e3Framed(7),
                          e3Plcp(8)
                      }
              ACCESS  read-write
              STATUS  mandatory
              ::= { dsx3ConfigEntry 5 }

          dsx3LineCoding OBJECT-TYPE
              SYNTAX  INTEGER {
                          dsx3Other(1),
                          dsx3B3ZS(2),
                          e3HDB3(3)
                      }
              ACCESS  read-write
              STATUS  mandatory
              ::= { dsx3ConfigEntry 6 }

          dsx3SendCode OBJECT-TYPE
                 SYNTAX  INTEGER {
                         dsx3SendNoCode(1),
                         dsx3SendLineCode(2),
                         dsx3SendPayloadCode(3),
                         dsx3SendResetCode(4),
                         dsx3SendDS1LoopCode(5),
                         dsx3SendTestPattern(6)
                         }
                 ACCESS  read-write
                 STATUS  mandatory
                 ::= { dsx3ConfigEntry 7 }

          dsx3CircuitIdentifier OBJECT-TYPE
              SYNTAX  DisplayString (SIZE (0..255))
              ACCESS  read-write
              STATUS  mandatory
              ::= { dsx3ConfigEntry 8 }

          dsx3LoopbackConfig OBJECT-TYPE
                 SYNTAX  INTEGER {
                           dsx3NoLoop(1),
                           dsx3PayloadLoop(2),
                           dsx3LineLoop(3),
                           dsx3OtherLoop(4)
                         }
                 ACCESS  read-write
                 STATUS  mandatory
                 ::= { dsx3ConfigEntry 9 }

          dsx3LineStatus OBJECT-TYPE
              SYNTAX  INTEGER (1..1023)
              ACCESS  read-only
              STATUS  mandatory
              ::= { dsx3ConfigEntry 10 }

          dsx3TransmitClockSource OBJECT-TYPE
              SYNTAX  INTEGER {
                          loopTiming(1),
                          localTiming(2),
                          throughTiming(3)
                      }
              ACCESS  read-write
              STATUS  mandatory
              ::= { dsx3ConfigEntry 11 }




          dsx3CurrentTable OBJECT-TYPE
              SYNTAX  SEQUENCE OF Dsx3CurrentEntry
              ACCESS  not-accessible
              STATUS  mandatory
              ::= { ds3 6 }

          dsx3CurrentEntry OBJECT-TYPE
              SYNTAX  Dsx3CurrentEntry
              ACCESS  not-accessible
              STATUS  mandatory
              INDEX   { dsx3CurrentIndex }
              ::= { dsx3CurrentTable 1 }







          Dsx3CurrentEntry ::=
              SEQUENCE {
                  dsx3CurrentIndex
                      INTEGER,
                  dsx3CurrentPESs
                      Gauge,
                  dsx3CurrentPSESs
                      Gauge,
                  dsx3CurrentSEFSs
                      Gauge,
                  dsx3CurrentUASs
                      Gauge,
                  dsx3CurrentLCVs
                      Gauge,
                  dsx3CurrentPCVs
                      Gauge,
                  dsx3CurrentLESs
                      Gauge,
                  dsx3CurrentCCVs
                      Gauge,
                  dsx3CurrentCESs
                      Gauge,
                  dsx3CurrentCSESs
                      Gauge
              }

          dsx3CurrentIndex OBJECT-TYPE
              SYNTAX  INTEGER (1..65535)
              ACCESS  read-only
              STATUS  mandatory
              ::= { dsx3CurrentEntry 1 }

          dsx3CurrentPESs OBJECT-TYPE
              SYNTAX  Gauge
              ACCESS  read-only
              STATUS  mandatory
              ::= { dsx3CurrentEntry 2 }





          dsx3CurrentPSESs OBJECT-TYPE
              SYNTAX  Gauge
              ACCESS  read-only
              STATUS  mandatory
              ::= { dsx3CurrentEntry 3 }

          dsx3CurrentSEFSs OBJECT-TYPE
              SYNTAX  Gauge
              ACCESS  read-only
              STATUS  mandatory
              ::= { dsx3CurrentEntry 4 }

          dsx3CurrentUASs OBJECT-TYPE
              SYNTAX  Gauge
              ACCESS  read-only
              STATUS  mandatory
              ::= { dsx3CurrentEntry 5 }

          dsx3CurrentLCVs OBJECT-TYPE
              SYNTAX  Gauge
              ACCESS  read-only
              STATUS  mandatory
              ::= { dsx3CurrentEntry 6 }

          dsx3CurrentPCVs OBJECT-TYPE
              SYNTAX  Gauge
              ACCESS  read-only
              STATUS  mandatory
              ::= { dsx3CurrentEntry 7 }

          dsx3CurrentLESs OBJECT-TYPE
              SYNTAX  Gauge
              ACCESS  read-only
              STATUS  mandatory
              ::= { dsx3CurrentEntry 8 }

          dsx3CurrentCCVs OBJECT-TYPE
              SYNTAX  Gauge
              ACCESS  read-only
              STATUS  mandatory
              ::= { dsx3CurrentEntry 9 }

          dsx3CurrentCESs OBJECT-TYPE
              SYNTAX  Gauge
              ACCESS  read-only
              STATUS  mandatory
              ::= { dsx3CurrentEntry 10 }

          dsx3CurrentCSESs OBJECT-TYPE
              SYNTAX  Gauge
              ACCESS  read-only
              STATUS  mandatory
              ::= { dsx3CurrentEntry 11 }









          dsx3IntervalTable OBJECT-TYPE
              SYNTAX  SEQUENCE OF Dsx3IntervalEntry
              ACCESS  not-accessible
              STATUS  mandatory
              ::= { ds3 7 }

          dsx3IntervalEntry OBJECT-TYPE
              SYNTAX  Dsx3IntervalEntry
              ACCESS  not-accessible
              STATUS  mandatory
              INDEX   { dsx3IntervalIndex, dsx3IntervalNumber }
              ::= { dsx3IntervalTable 1 }

          Dsx3IntervalEntry ::=
              SEQUENCE {
                  dsx3IntervalIndex
                      INTEGER,
                  dsx3IntervalNumber
                      INTEGER,
                  dsx3IntervalPESs
                      Gauge,
                  dsx3IntervalPSESs
                      Gauge,
                  dsx3IntervalSEFSs
                      Gauge,
                  dsx3IntervalUASs
                      Gauge,
                  dsx3IntervalLCVs
                      Gauge,
                  dsx3IntervalPCVs
                      Gauge,
                  dsx3IntervalLESs
                      Gauge,
                  dsx3IntervalCCVs
                      Gauge,
                  dsx3IntervalCESs
                      Gauge,
                  dsx3IntervalCSESs
                      Gauge
              }






          dsx3IntervalIndex OBJECT-TYPE
              SYNTAX  INTEGER (1..65535)
              ACCESS  read-only
              STATUS  mandatory
              ::= { dsx3IntervalEntry 1 }

          dsx3IntervalNumber OBJECT-TYPE
              SYNTAX  INTEGER (1..96)
              ACCESS  read-only
              STATUS  mandatory
              ::= { dsx3IntervalEntry 2 }

          dsx3IntervalPESs OBJECT-TYPE
              SYNTAX  Gauge
              ACCESS  read-only
              STATUS  mandatory
              ::= { dsx3IntervalEntry 3 }

          dsx3IntervalPSESs OBJECT-TYPE
              SYNTAX  Gauge
              ACCESS  read-only
              STATUS  mandatory
              ::= { dsx3IntervalEntry 4 }

          dsx3IntervalSEFSs OBJECT-TYPE
              SYNTAX  Gauge





              ACCESS  read-only
              STATUS  mandatory
              ::= { dsx3IntervalEntry 5 }

          dsx3IntervalUASs OBJECT-TYPE
              SYNTAX  Gauge
              ACCESS  read-only
              STATUS  mandatory
              ::= { dsx3IntervalEntry 6 }

          dsx3IntervalLCVs OBJECT-TYPE
              SYNTAX  Gauge
              ACCESS  read-only
              STATUS  mandatory
              ::= { dsx3IntervalEntry 7 }

          dsx3IntervalPCVs OBJECT-TYPE
              SYNTAX  Gauge
              ACCESS  read-only
              STATUS  mandatory
              ::= { dsx3IntervalEntry 8 }

          dsx3IntervalLESs OBJECT-TYPE
              SYNTAX  Gauge
              ACCESS  read-only
              STATUS  mandatory
              ::= { dsx3IntervalEntry 9 }

          dsx3IntervalCCVs OBJECT-TYPE
              SYNTAX  Gauge
              ACCESS  read-only
              STATUS  mandatory
              ::= { dsx3IntervalEntry 10 }

          dsx3IntervalCESs OBJECT-TYPE
              SYNTAX  Gauge
              ACCESS  read-only
              STATUS  mandatory
              ::= { dsx3IntervalEntry 11 }

          dsx3IntervalCSESs OBJECT-TYPE
              SYNTAX  Gauge
              ACCESS  read-only
              STATUS  mandatory
              ::= { dsx3IntervalEntry 12 }




          dsx3TotalTable OBJECT-TYPE
              SYNTAX  SEQUENCE OF Dsx3TotalEntry
              ACCESS  not-accessible
              STATUS  mandatory





              ::= { ds3 8 }

          dsx3TotalEntry OBJECT-TYPE
              SYNTAX  Dsx3TotalEntry
              ACCESS  not-accessible
              STATUS  mandatory
              INDEX   { dsx3TotalIndex }
              ::= { dsx3TotalTable 1 }

          Dsx3TotalEntry ::=
              SEQUENCE {
                  dsx3TotalIndex
                      INTEGER,
                  dsx3TotalPESs
                      Gauge,
                  dsx3TotalPSESs
                      Gauge,
                  dsx3TotalSEFSs
                      Gauge,
                  dsx3TotalUASs
                      Gauge,
                  dsx3TotalLCVs
                      Gauge,
                  dsx3TotalPCVs
                      Gauge,
                  dsx3TotalLESs
                      Gauge,
                  dsx3TotalCCVs
                      Gauge,
                  dsx3TotalCESs
                      Gauge,
                  dsx3TotalCSESs
                      Gauge
              }

          dsx3TotalIndex OBJECT-TYPE
              SYNTAX  INTEGER (1..65535)
              ACCESS  read-only
              STATUS  mandatory





              ::= { dsx3TotalEntry 1 }

          dsx3TotalPESs OBJECT-TYPE
              SYNTAX  Gauge
              ACCESS  read-only
              STATUS  mandatory
              ::= { dsx3TotalEntry 2 }

          dsx3TotalPSESs OBJECT-TYPE
              SYNTAX  Gauge
              ACCESS  read-only
              STATUS  mandatory
              ::= { dsx3TotalEntry 3 }

          dsx3TotalSEFSs OBJECT-TYPE
              SYNTAX  Gauge
              ACCESS  read-only
              STATUS  mandatory
              ::= { dsx3TotalEntry 4 }

          dsx3TotalUASs OBJECT-TYPE
              SYNTAX  Gauge
              ACCESS  read-only
              STATUS  mandatory
              ::= { dsx3TotalEntry 5 }

          dsx3TotalLCVs OBJECT-TYPE
              SYNTAX  Gauge
              ACCESS  read-only
              STATUS  mandatory
              ::= { dsx3TotalEntry 6 }

          dsx3TotalPCVs OBJECT-TYPE
              SYNTAX  Gauge
              ACCESS  read-only
              STATUS  mandatory
              ::= { dsx3TotalEntry 7 }

          dsx3TotalLESs OBJECT-TYPE
              SYNTAX  Gauge
              ACCESS  read-only
              STATUS  mandatory
              ::= { dsx3TotalEntry 8 }

          dsx3TotalCCVs OBJECT-TYPE
              SYNTAX  Gauge
              ACCESS  read-only
              STATUS  mandatory
              ::= { dsx3TotalEntry 9 }

          dsx3TotalCESs OBJECT-TYPE
              SYNTAX  Gauge
              ACCESS  read-only
              STATUS  mandatory
              ::= { dsx3TotalEntry 10 }

          dsx3TotalCSESs OBJECT-TYPE
              SYNTAX  Gauge
              ACCESS  read-only





              STATUS  mandatory
              ::= { dsx3TotalEntry 11 }







          dsx3FarEndConfigTable OBJECT-TYPE
              SYNTAX  SEQUENCE OF Dsx3FarEndConfigEntry
              ACCESS  not-accessible
              STATUS  mandatory
              ::= { ds3 9 }

          dsx3FarEndConfigEntry OBJECT-TYPE
              SYNTAX  Dsx3FarEndConfigEntry
              ACCESS  not-accessible
              STATUS  mandatory
              INDEX   { dsx3FarEndLineIndex }
              ::= { dsx3FarEndConfigTable 1 }

          Dsx3FarEndConfigEntry ::=
              SEQUENCE {
                  dsx3FarEndLineIndex
                      INTEGER,
                  dsx3FarEndEquipCode





                      DisplayString,
                  dsx3FarEndLocationIDCode
                      DisplayString,
                  dsx3FarEndFrameIDCode
                      DisplayString,
                  dsx3FarEndUnitCode
                      DisplayString,
                  dsx3FarEndFacilityIDCode
                      DisplayString
               }

          dsx3FarEndLineIndex OBJECT-TYPE
              SYNTAX  INTEGER (1..65535)
              ACCESS  read-only
              STATUS  mandatory
             ::= { dsx3FarEndConfigEntry 1 }

          dsx3FarEndEquipCode OBJECT-TYPE
              SYNTAX  DisplayString (SIZE (0..10))
              ACCESS  read-write
              STATUS  mandatory
              ::= { dsx3FarEndConfigEntry 2 }

          dsx3FarEndLocationIDCode OBJECT-TYPE
              SYNTAX  DisplayString (SIZE (0..11))
              ACCESS  read-write
              STATUS  mandatory
              ::= { dsx3FarEndConfigEntry 3 }






          dsx3FarEndFrameIDCode OBJECT-TYPE
              SYNTAX  DisplayString (SIZE (0..10))
              ACCESS  read-write
              STATUS  mandatory
              ::= { dsx3FarEndConfigEntry 4 }

          dsx3FarEndUnitCode OBJECT-TYPE
              SYNTAX  DisplayString (SIZE (0..6))
              ACCESS  read-write
              STATUS  mandatory
              ::= { dsx3FarEndConfigEntry 5 }

          dsx3FarEndFacilityIDCode OBJECT-TYPE
              SYNTAX  DisplayString (SIZE (0..38))
              ACCESS  read-write
              STATUS  mandatory
              ::= { dsx3FarEndConfigEntry 6 }




          dsx3FarEndCurrentTable OBJECT-TYPE
              SYNTAX  SEQUENCE OF Dsx3FarEndCurrentEntry
              ACCESS  not-accessible
              STATUS  mandatory
              ::= { ds3 10 }





          dsx3FarEndCurrentEntry OBJECT-TYPE
              SYNTAX  Dsx3FarEndCurrentEntry
              ACCESS  not-accessible
              STATUS  mandatory
              INDEX   { dsx3FarEndCurrentIndex }
              ::= { dsx3FarEndCurrentTable 1 }

          Dsx3FarEndCurrentEntry ::=
              SEQUENCE {
                  dsx3FarEndCurrentIndex
                      INTEGER,
                  dsx3FarEndTimeElapsed
                      INTEGER,
                  dsx3FarEndValidIntervals
                      INTEGER,
                  dsx3FarEndCurrentCESs
                      Gauge,
                  dsx3FarEndCurrentCSESs
                      Gauge,
                  dsx3FarEndCurrentCCVs
                      Gauge,
                  dsx3FarEndCurrentUASs
                      Gauge
              }

           dsx3FarEndCurrentIndex OBJECT-TYPE
              SYNTAX  INTEGER (1..65535)
              ACCESS  read-only
              STATUS  mandatory
              ::= { dsx3FarEndCurrentEntry 1 }

          dsx3FarEndTimeElapsed OBJECT-TYPE
              SYNTAX  INTEGER (0..899)
              ACCESS  read-only
              STATUS  mandatory





              ::= { dsx3FarEndCurrentEntry 2 }

          dsx3FarEndValidIntervals OBJECT-TYPE
              SYNTAX  INTEGER (0..96)
              ACCESS  read-only
              STATUS  mandatory
              ::= { dsx3FarEndCurrentEntry 3 }

          dsx3FarEndCurrentCESs OBJECT-TYPE
              SYNTAX  Gauge
              ACCESS  read-only
              STATUS  mandatory
              ::= { dsx3FarEndCurrentEntry 4 }

          dsx3FarEndCurrentCSESs OBJECT-TYPE
              SYNTAX  Gauge
              ACCESS  read-only
              STATUS  mandatory
              ::= { dsx3FarEndCurrentEntry 5 }

          dsx3FarEndCurrentCCVs OBJECT-TYPE
              SYNTAX  Gauge
              ACCESS  read-only
              STATUS  mandatory
              ::= { dsx3FarEndCurrentEntry 6 }






          dsx3FarEndCurrentUASs OBJECT-TYPE
              SYNTAX  Gauge
              ACCESS  read-only
              STATUS  mandatory
              ::= { dsx3FarEndCurrentEntry 7 }




          dsx3FarEndIntervalTable OBJECT-TYPE
              SYNTAX  SEQUENCE OF Dsx3FarEndIntervalEntry
              ACCESS  not-accessible
              STATUS  mandatory
              ::= { ds3 11 }

          dsx3FarEndIntervalEntry OBJECT-TYPE
              SYNTAX  Dsx3FarEndIntervalEntry
              ACCESS  not-accessible
              STATUS  mandatory
              INDEX   { dsx3FarEndIntervalIndex,
                        dsx3FarEndIntervalNumber }
              ::= { dsx3FarEndIntervalTable 1 }

          Dsx3FarEndIntervalEntry ::=
              SEQUENCE {
                   dsx3FarEndIntervalIndex
                        INTEGER,
                   dsx3FarEndIntervalNumber
                        INTEGER,
                   dsx3FarEndIntervalCESs
                        Gauge,
                   dsx3FarEndIntervalCSESs
                        Gauge,





                   dsx3FarEndIntervalCCVs
                        Gauge,
                   dsx3FarEndIntervalUASs
                        Gauge
              }

          dsx3FarEndIntervalIndex OBJECT-TYPE
              SYNTAX  INTEGER (1..65535)
              ACCESS  read-only
              STATUS  mandatory
              ::= { dsx3FarEndIntervalEntry 1 }

          dsx3FarEndIntervalNumber OBJECT-TYPE
             SYNTAX  INTEGER (1..96)
             ACCESS  read-only
             STATUS  mandatory
             ::= { dsx3FarEndIntervalEntry 2 }

          dsx3FarEndIntervalCESs OBJECT-TYPE
             SYNTAX  Gauge
             ACCESS  read-only
             STATUS  mandatory
            ::= { dsx3FarEndIntervalEntry 3 }

          dsx3FarEndIntervalCSESs OBJECT-TYPE
             SYNTAX  Gauge
             ACCESS  read-only
             STATUS  mandatory
            ::= { dsx3FarEndIntervalEntry 4 }

          dsx3FarEndIntervalCCVs OBJECT-TYPE
              SYNTAX  Gauge
              ACCESS  read-only
              STATUS  mandatory
              ::= { dsx3FarEndIntervalEntry 5 }

          dsx3FarEndIntervalUASs OBJECT-TYPE
              SYNTAX  Gauge
              ACCESS  read-only
              STATUS  mandatory
              ::= { dsx3FarEndIntervalEntry 6 }




          dsx3FarEndTotalTable OBJECT-TYPE
              SYNTAX  SEQUENCE OF Dsx3FarEndTotalEntry
              ACCESS  not-accessible
              STATUS  mandatory
              ::= { ds3 12 }

          dsx3FarEndTotalEntry OBJECT-TYPE
              SYNTAX  Dsx3FarEndTotalEntry





              ACCESS  not-accessible
              STATUS  mandatory
              INDEX   { dsx3FarEndTotalIndex }
              ::= { dsx3FarEndTotalTable 1 }

          Dsx3FarEndTotalEntry ::=
              SEQUENCE {
                  dsx3FarEndTotalIndex
                      INTEGER,
                  dsx3FarEndTotalCESs
                      Gauge,
                  dsx3FarEndTotalCSESs
                      Gauge,
                  dsx3FarEndTotalCCVs
                      Gauge,
                  dsx3FarEndTotalUASs
                      Gauge
              }

          dsx3FarEndTotalIndex OBJECT-TYPE
              SYNTAX  INTEGER (1..65535)
              ACCESS  read-only
              STATUS  mandatory
              ::= { dsx3FarEndTotalEntry 1 }

          dsx3FarEndTotalCESs OBJECT-TYPE
             SYNTAX  Gauge
             ACCESS  read-only
             STATUS  mandatory
             ::= { dsx3FarEndTotalEntry 2 }

          dsx3FarEndTotalCSESs OBJECT-TYPE
             SYNTAX  Gauge
             ACCESS  read-only
             STATUS  mandatory





             ::= { dsx3FarEndTotalEntry 3 }

          dsx3FarEndTotalCCVs OBJECT-TYPE
             SYNTAX  Gauge
             ACCESS  read-only
             STATUS  mandatory
             ::= { dsx3FarEndTotalEntry 4 }

          dsx3FarEndTotalUASs OBJECT-TYPE
             SYNTAX  Gauge
             ACCESS  read-only
             STATUS  mandatory
             ::= { dsx3FarEndTotalEntry 5 }














          dsx3FracTable OBJECT-TYPE
              SYNTAX  SEQUENCE OF Dsx3FracEntry
              ACCESS  not-accessible
              STATUS  mandatory
              ::= { ds3 13 }

          dsx3FracEntry OBJECT-TYPE
               SYNTAX  Dsx3FracEntry
               ACCESS  not-accessible
               STATUS  mandatory
              INDEX   { dsx3FracIndex, dsx3FracNumber }
              ::= { dsx3FracTable 1 }

          Dsx3FracEntry ::=
              SEQUENCE {
                  dsx3FracIndex
                      INTEGER,
                  dsx3FracNumber
                      INTEGER,





                  dsx3FracIfIndex
                      INTEGER
              }


          dsx3FracIndex OBJECT-TYPE
              SYNTAX  INTEGER (1..'7fffffff'h)
              ACCESS  read-only
              STATUS  mandatory
             ::= { dsx3FracEntry 1 }

          dsx3FracNumber OBJECT-TYPE
              SYNTAX  INTEGER (1..31)
              ACCESS  read-only
              STATUS  mandatory
             ::= { dsx3FracEntry 2 }

          dsx3FracIfIndex OBJECT-TYPE
              SYNTAX  INTEGER (1..'7fffffff'h)
              ACCESS  read-write
              STATUS  mandatory
             ::= { dsx3FracEntry 3 }



          END
