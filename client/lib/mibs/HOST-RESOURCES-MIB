HOST-RESOURCES-MIB DEFINITIONS ::= BEGIN

   IMPORTS
   MODULE-IDENTITY, OBJECT-TYPE, mib-2,
   Integer32, Counter32, Gauge32, TimeTicks  FROM SNMPv2-SMI

   TEXTUAL-CONVENTION, DisplayString,
   TruthValue, DateAndTime, AutonomousType   FROM SNMPv2-TC

   MODULE-COMPLIANCE, OBJECT-GROUP           FROM SNMPv2-CONF

   InterfaceIndexOrZero                      FROM IF-MIB;

   hostResourcesMibModule MODULE-IDENTITY
      LAST-UPDATED "200003060000Z"    -- 6 March 2000
      ORGANIZATION "IETF Host Resources MIB Working Group"



      ::= { hrMIBAdminInfo 1 }

   host     OBJECT IDENTIFIER ::= { mib-2 25 }

   hrSystem        OBJECT IDENTIFIER ::= { host 1 }
   hrStorage       OBJECT IDENTIFIER ::= { host 2 }
   hrDevice        OBJECT IDENTIFIER ::= { host 3 }
   hrSWRun         OBJECT IDENTIFIER ::= { host 4 }
   hrSWRunPerf     OBJECT IDENTIFIER ::= { host 5 }
   hrSWInstalled   OBJECT IDENTIFIER ::= { host 6 }
   hrMIBAdminInfo  OBJECT IDENTIFIER ::= { host 7 }


   KBytes ::= TEXTUAL-CONVENTION
       STATUS current
       SYNTAX Integer32 (0..2147483647)

   ProductID ::= TEXTUAL-CONVENTION
       STATUS current
       SYNTAX OBJECT IDENTIFIER


   InternationalDisplayString ::= TEXTUAL-CONVENTION
       STATUS current
       SYNTAX OCTET STRING


   hrSystemUptime OBJECT-TYPE
       SYNTAX     TimeTicks
       MAX-ACCESS read-only
       STATUS     current
       ::= { hrSystem 1 }

   hrSystemDate OBJECT-TYPE
       SYNTAX     DateAndTime
       MAX-ACCESS read-write
       STATUS     current
       ::= { hrSystem 2 }

   hrSystemInitialLoadDevice OBJECT-TYPE
       SYNTAX     Integer32 (1..2147483647)
       MAX-ACCESS read-write
       STATUS     current
       ::= { hrSystem 3 }

   hrSystemInitialLoadParameters OBJECT-TYPE
       SYNTAX     InternationalDisplayString (SIZE (0..128))
       MAX-ACCESS read-write
       STATUS     current
       ::= { hrSystem 4 }

   hrSystemNumUsers OBJECT-TYPE





       SYNTAX     Gauge32
       MAX-ACCESS read-only
       STATUS     current
       ::= { hrSystem 5 }

   hrSystemProcesses OBJECT-TYPE
       SYNTAX     Gauge32
       MAX-ACCESS read-only
       STATUS     current
       ::= { hrSystem 6 }

   hrSystemMaxProcesses OBJECT-TYPE
       SYNTAX     Integer32 (0..2147483647)
       MAX-ACCESS read-only
       STATUS     current
       ::= { hrSystem 7 }


   hrStorageTypes          OBJECT IDENTIFIER ::= { hrStorage 1 }

   hrMemorySize OBJECT-TYPE
       SYNTAX     KBytes
       UNITS      "KBytes"
       MAX-ACCESS read-only
       STATUS     current
       ::= { hrStorage 2 }






   hrStorageTable OBJECT-TYPE
       SYNTAX     SEQUENCE OF HrStorageEntry
       MAX-ACCESS not-accessible
       STATUS     current
       ::= { hrStorage 3 }

   hrStorageEntry OBJECT-TYPE
       SYNTAX     HrStorageEntry
       MAX-ACCESS not-accessible
       STATUS     current
       INDEX { hrStorageIndex }
       ::= { hrStorageTable 1 }

   HrStorageEntry ::= SEQUENCE {
           hrStorageIndex               Integer32,





           hrStorageType                AutonomousType,
           hrStorageDescr               DisplayString,
           hrStorageAllocationUnits     Integer32,
           hrStorageSize                Integer32,
           hrStorageUsed                Integer32,
           hrStorageAllocationFailures  Counter32
       }

   hrStorageIndex OBJECT-TYPE
       SYNTAX     Integer32 (1..2147483647)
       MAX-ACCESS read-only
       STATUS     current
       ::= { hrStorageEntry 1 }

   hrStorageType OBJECT-TYPE
       SYNTAX     AutonomousType
       MAX-ACCESS read-only
       STATUS     current
       ::= { hrStorageEntry 2 }

   hrStorageDescr OBJECT-TYPE
       SYNTAX     DisplayString
       MAX-ACCESS read-only
       STATUS     current
       ::= { hrStorageEntry 3 }

   hrStorageAllocationUnits OBJECT-TYPE
       SYNTAX     Integer32 (1..2147483647)
       UNITS      "Bytes"
       MAX-ACCESS read-only
       STATUS     current
       ::= { hrStorageEntry 4 }

   hrStorageSize OBJECT-TYPE





       SYNTAX     Integer32 (0..2147483647)
       MAX-ACCESS read-write
       STATUS     current
       ::= { hrStorageEntry 5 }

   hrStorageUsed OBJECT-TYPE
       SYNTAX     Integer32 (0..2147483647)
       MAX-ACCESS read-only
       STATUS     current
       ::= { hrStorageEntry 6 }

   hrStorageAllocationFailures OBJECT-TYPE
       SYNTAX     Counter32
       MAX-ACCESS read-only
       STATUS     current
       ::= { hrStorageEntry 7 }







   hrDeviceTypes             OBJECT IDENTIFIER ::= { hrDevice 1 }

   hrDeviceTable OBJECT-TYPE
       SYNTAX     SEQUENCE OF HrDeviceEntry
       MAX-ACCESS not-accessible
       STATUS     current
       ::= { hrDevice 2 }

   hrDeviceEntry OBJECT-TYPE
       SYNTAX     HrDeviceEntry
       MAX-ACCESS not-accessible
       STATUS     current
       INDEX { hrDeviceIndex }
       ::= { hrDeviceTable 1 }

   HrDeviceEntry ::= SEQUENCE {
           hrDeviceIndex           Integer32,
           hrDeviceType            AutonomousType,
           hrDeviceDescr           DisplayString,
           hrDeviceID              ProductID,
           hrDeviceStatus          INTEGER,
           hrDeviceErrors          Counter32
       }

   hrDeviceIndex OBJECT-TYPE
       SYNTAX     Integer32 (1..2147483647)
       MAX-ACCESS read-only
       STATUS     current
       ::= { hrDeviceEntry 1 }

   hrDeviceType OBJECT-TYPE
       SYNTAX     AutonomousType
       MAX-ACCESS read-only
       STATUS     current
       ::= { hrDeviceEntry 2 }

   hrDeviceDescr OBJECT-TYPE
       SYNTAX     DisplayString (SIZE (0..64))
       MAX-ACCESS read-only
       STATUS     current
       ::= { hrDeviceEntry 3 }

   hrDeviceID OBJECT-TYPE
       SYNTAX     ProductID
       MAX-ACCESS read-only
       STATUS     current
       ::= { hrDeviceEntry 4 }

   hrDeviceStatus OBJECT-TYPE
       SYNTAX     INTEGER {
                      unknown(1),
                      running(2),
                      warning(3),
                      testing(4),
                      down(5)





                  }
       MAX-ACCESS read-only
       STATUS     current
       ::= { hrDeviceEntry 5 }

   hrDeviceErrors OBJECT-TYPE
       SYNTAX     Counter32
       MAX-ACCESS read-only
       STATUS     current
       ::= { hrDeviceEntry 6 }

   hrProcessorTable OBJECT-TYPE
       SYNTAX     SEQUENCE OF HrProcessorEntry
       MAX-ACCESS not-accessible
       STATUS     current
       ::= { hrDevice 3 }






   hrProcessorEntry OBJECT-TYPE
       SYNTAX     HrProcessorEntry
       MAX-ACCESS not-accessible
       STATUS     current
       INDEX { hrDeviceIndex }
       ::= { hrProcessorTable 1 }

   HrProcessorEntry ::= SEQUENCE {
           hrProcessorFrwID            ProductID,
           hrProcessorLoad             Integer32
       }

   hrProcessorFrwID OBJECT-TYPE
       SYNTAX     ProductID
       MAX-ACCESS read-only
       STATUS     current
       ::= { hrProcessorEntry 1 }

   hrProcessorLoad OBJECT-TYPE
       SYNTAX     Integer32 (0..100)
       MAX-ACCESS read-only
       STATUS     current
       ::= { hrProcessorEntry 2 }

   hrNetworkTable OBJECT-TYPE
       SYNTAX     SEQUENCE OF HrNetworkEntry
       MAX-ACCESS not-accessible
       STATUS     current
       ::= { hrDevice 4 }

   hrNetworkEntry OBJECT-TYPE
       SYNTAX     HrNetworkEntry
       MAX-ACCESS not-accessible
       STATUS     current
       INDEX { hrDeviceIndex }
       ::= { hrNetworkTable 1 }

   HrNetworkEntry ::= SEQUENCE {
           hrNetworkIfIndex    InterfaceIndexOrZero
       }

   hrNetworkIfIndex OBJECT-TYPE
       SYNTAX     InterfaceIndexOrZero
       MAX-ACCESS read-only
       STATUS     current
       ::= { hrNetworkEntry 1 }

   hrPrinterTable OBJECT-TYPE
       SYNTAX     SEQUENCE OF HrPrinterEntry
       MAX-ACCESS not-accessible
       STATUS     current
       ::= { hrDevice 5 }





   hrPrinterEntry OBJECT-TYPE
       SYNTAX     HrPrinterEntry
       MAX-ACCESS not-accessible
       STATUS     current
       INDEX { hrDeviceIndex }
       ::= { hrPrinterTable 1 }

   HrPrinterEntry ::= SEQUENCE {
           hrPrinterStatus             INTEGER,
           hrPrinterDetectedErrorState OCTET STRING
       }

   hrPrinterStatus OBJECT-TYPE
       SYNTAX     INTEGER {
                      other(1),
                      unknown(2),
                      idle(3),
                      printing(4),
                      warmup(5)
                  }
       MAX-ACCESS read-only
       STATUS     current
       ::= { hrPrinterEntry 1 }

   hrPrinterDetectedErrorState OBJECT-TYPE
       SYNTAX     OCTET STRING
       MAX-ACCESS read-only
       STATUS     current
       ::= { hrPrinterEntry 2 }

   hrDiskStorageTable OBJECT-TYPE
       SYNTAX     SEQUENCE OF HrDiskStorageEntry
       MAX-ACCESS not-accessible
       STATUS     current
       ::= { hrDevice 6 }

   hrDiskStorageEntry OBJECT-TYPE
       SYNTAX     HrDiskStorageEntry
       MAX-ACCESS not-accessible
       STATUS     current





       INDEX { hrDeviceIndex }
       ::= { hrDiskStorageTable 1 }

   HrDiskStorageEntry ::= SEQUENCE {
           hrDiskStorageAccess         INTEGER,
           hrDiskStorageMedia          INTEGER,
           hrDiskStorageRemoveble      TruthValue,
           hrDiskStorageCapacity       KBytes
       }

   hrDiskStorageAccess OBJECT-TYPE
       SYNTAX     INTEGER {
                      readWrite(1),
                      readOnly(2)
                  }
       MAX-ACCESS read-only
       STATUS     current
       ::= { hrDiskStorageEntry 1 }

   hrDiskStorageMedia OBJECT-TYPE
       SYNTAX     INTEGER {
                      other(1),
                      unknown(2),
                      hardDisk(3),
                      floppyDisk(4),
                      opticalDiskROM(5),
                      opticalDiskWORM(6),     -- Write Once Read Many
                      opticalDiskRW(7),
                      ramDisk(8)
                  }
       MAX-ACCESS read-only
       STATUS     current





       ::= { hrDiskStorageEntry 2 }

   hrDiskStorageRemoveble OBJECT-TYPE
       SYNTAX     TruthValue
       MAX-ACCESS read-only
       STATUS     current
       ::= { hrDiskStorageEntry 3 }

   hrDiskStorageCapacity OBJECT-TYPE
       SYNTAX     KBytes
       UNITS      "KBytes"
       MAX-ACCESS read-only
       STATUS     current
       ::= { hrDiskStorageEntry 4 }

   hrPartitionTable OBJECT-TYPE
       SYNTAX     SEQUENCE OF HrPartitionEntry
       MAX-ACCESS not-accessible
       STATUS     current
       ::= { hrDevice 7 }

   hrPartitionEntry OBJECT-TYPE
       SYNTAX     HrPartitionEntry
       MAX-ACCESS not-accessible
       STATUS     current
       INDEX { hrDeviceIndex, hrPartitionIndex }
       ::= { hrPartitionTable 1 }





   HrPartitionEntry ::= SEQUENCE {
           hrPartitionIndex                Integer32,
           hrPartitionLabel                InternationalDisplayString,
           hrPartitionID                   OCTET STRING,
           hrPartitionSize                 KBytes,
           hrPartitionFSIndex              Integer32
       }

   hrPartitionIndex OBJECT-TYPE
       SYNTAX     Integer32 (1..2147483647)
       MAX-ACCESS read-only
       STATUS     current
       ::= { hrPartitionEntry 1 }

   hrPartitionLabel OBJECT-TYPE
       SYNTAX     InternationalDisplayString (SIZE (0..128))
       MAX-ACCESS read-only
       STATUS     current
       ::= { hrPartitionEntry 2 }

   hrPartitionID OBJECT-TYPE
       SYNTAX     OCTET STRING
       MAX-ACCESS read-only
       STATUS     current
       ::= { hrPartitionEntry 3 }

   hrPartitionSize OBJECT-TYPE
       SYNTAX     KBytes
       UNITS      "KBytes"
       MAX-ACCESS read-only
       STATUS     current
       ::= { hrPartitionEntry 4 }

   hrPartitionFSIndex OBJECT-TYPE





       SYNTAX     Integer32 (0..2147483647)
       MAX-ACCESS read-only
       STATUS     current
       ::= { hrPartitionEntry 5 }


   hrFSTypes               OBJECT IDENTIFIER ::= { hrDevice 9 }

   hrFSTable OBJECT-TYPE
       SYNTAX     SEQUENCE OF HrFSEntry
       MAX-ACCESS not-accessible
       STATUS     current
       ::= { hrDevice 8 }

   hrFSEntry OBJECT-TYPE
       SYNTAX     HrFSEntry
       MAX-ACCESS not-accessible
       STATUS     current
       INDEX { hrFSIndex }
       ::= { hrFSTable 1 }






   HrFSEntry ::= SEQUENCE {
           hrFSIndex                   Integer32,
           hrFSMountPoint              InternationalDisplayString,
           hrFSRemoteMountPoint        InternationalDisplayString,
           hrFSType                    AutonomousType,
           hrFSAccess                  INTEGER,
           hrFSBootable                TruthValue,
           hrFSStorageIndex            Integer32,
           hrFSLastFullBackupDate      DateAndTime,
           hrFSLastPartialBackupDate   DateAndTime
       }

   hrFSIndex OBJECT-TYPE
       SYNTAX     Integer32 (1..2147483647)
       MAX-ACCESS read-only
       STATUS     current
       ::= { hrFSEntry 1 }

   hrFSMountPoint OBJECT-TYPE
       SYNTAX     InternationalDisplayString (SIZE(0..128))
       MAX-ACCESS read-only
       STATUS     current
       ::= { hrFSEntry 2 }

   hrFSRemoteMountPoint OBJECT-TYPE
       SYNTAX     InternationalDisplayString (SIZE(0..128))
       MAX-ACCESS read-only
       STATUS     current
       ::= { hrFSEntry 3 }

   hrFSType OBJECT-TYPE
       SYNTAX     AutonomousType
       MAX-ACCESS read-only
       STATUS     current
       ::= { hrFSEntry 4 }

   hrFSAccess OBJECT-TYPE
       SYNTAX     INTEGER {
                      readWrite(1),
                      readOnly(2)
                  }
       MAX-ACCESS read-only
       STATUS     current
       ::= { hrFSEntry 5 }

   hrFSBootable OBJECT-TYPE
       SYNTAX     TruthValue
       MAX-ACCESS read-only
       STATUS     current
       ::= { hrFSEntry 6 }

   hrFSStorageIndex OBJECT-TYPE
       SYNTAX     Integer32 (0..2147483647)
       MAX-ACCESS read-only
       STATUS     current
       ::= { hrFSEntry 7 }

   hrFSLastFullBackupDate OBJECT-TYPE
       SYNTAX     DateAndTime
       MAX-ACCESS read-write
       STATUS     current
       ::= { hrFSEntry 8 }

   hrFSLastPartialBackupDate OBJECT-TYPE
       SYNTAX     DateAndTime
       MAX-ACCESS read-write
       STATUS     current
       ::= { hrFSEntry 9 }


   hrSWOSIndex OBJECT-TYPE
       SYNTAX     Integer32 (1..2147483647)
       MAX-ACCESS read-only
       STATUS     current
       ::= { hrSWRun 1 }

   hrSWRunTable OBJECT-TYPE
       SYNTAX     SEQUENCE OF HrSWRunEntry
       MAX-ACCESS not-accessible
       STATUS     current





       ::= { hrSWRun 2 }

   hrSWRunEntry OBJECT-TYPE
       SYNTAX     HrSWRunEntry
       MAX-ACCESS not-accessible
       STATUS     current
       INDEX { hrSWRunIndex }
       ::= { hrSWRunTable 1 }

   HrSWRunEntry ::= SEQUENCE {
           hrSWRunIndex       Integer32,
           hrSWRunName        InternationalDisplayString,
           hrSWRunID          ProductID,
           hrSWRunPath        InternationalDisplayString,
           hrSWRunParameters  InternationalDisplayString,
           hrSWRunType        INTEGER,
           hrSWRunStatus      INTEGER
       }

   hrSWRunIndex OBJECT-TYPE
       SYNTAX     Integer32 (1..2147483647)
       MAX-ACCESS read-only
       STATUS     current
       ::= { hrSWRunEntry 1 }

   hrSWRunName OBJECT-TYPE
       SYNTAX     InternationalDisplayString (SIZE (0..64))
       MAX-ACCESS read-only





       STATUS     current
       ::= { hrSWRunEntry 2 }

   hrSWRunID OBJECT-TYPE
       SYNTAX     ProductID
       MAX-ACCESS read-only
       STATUS     current
       ::= { hrSWRunEntry 3 }

   hrSWRunPath OBJECT-TYPE
       SYNTAX     InternationalDisplayString (SIZE(0..128))
       MAX-ACCESS read-only
       STATUS     current
       ::= { hrSWRunEntry 4 }

   hrSWRunParameters OBJECT-TYPE
       SYNTAX     InternationalDisplayString (SIZE(0..128))
       MAX-ACCESS read-only
       STATUS     current
       ::= { hrSWRunEntry 5 }

   hrSWRunType OBJECT-TYPE
       SYNTAX     INTEGER {
                      unknown(1),
                      operatingSystem(2),
                      deviceDriver(3),
                      application(4)
                  }
       MAX-ACCESS read-only
       STATUS     current





       ::= { hrSWRunEntry 6 }

   hrSWRunStatus OBJECT-TYPE
       SYNTAX     INTEGER {
                      running(1),
                      runnable(2),    -- waiting for resource
                      notRunnable(3), -- loaded but waiting for event
                      invalid(4)      -- not loaded
                  }
       MAX-ACCESS read-write
       STATUS     current
       ::= { hrSWRunEntry 7 }


   hrSWRunPerfTable OBJECT-TYPE
       SYNTAX     SEQUENCE OF HrSWRunPerfEntry
       MAX-ACCESS not-accessible
       STATUS     current
       ::= { hrSWRunPerf 1 }

   hrSWRunPerfEntry OBJECT-TYPE
       SYNTAX     HrSWRunPerfEntry
       MAX-ACCESS not-accessible
       STATUS     current
       AUGMENTS { hrSWRunEntry }  -- This table augments information in
       ::= { hrSWRunPerfTable 1 }

   HrSWRunPerfEntry ::= SEQUENCE {
           hrSWRunPerfCPU          Integer32,





           hrSWRunPerfMem          KBytes
   }

   hrSWRunPerfCPU OBJECT-TYPE
       SYNTAX     Integer32 (0..2147483647)
       MAX-ACCESS read-only
       STATUS     current
       ::= { hrSWRunPerfEntry 1 }

   hrSWRunPerfMem OBJECT-TYPE
       SYNTAX     KBytes
       UNITS      "KBytes"
       MAX-ACCESS read-only
       STATUS     current
       ::= { hrSWRunPerfEntry 2 }


   hrSWInstalledLastChange OBJECT-TYPE
       SYNTAX     TimeTicks
       MAX-ACCESS read-only





       STATUS     current
       ::= { hrSWInstalled 1 }

   hrSWInstalledLastUpdateTime OBJECT-TYPE
       SYNTAX     TimeTicks
       MAX-ACCESS read-only
       STATUS     current
       ::= { hrSWInstalled 2 }

   hrSWInstalledTable OBJECT-TYPE
       SYNTAX     SEQUENCE OF HrSWInstalledEntry
       MAX-ACCESS not-accessible
       STATUS     current
       ::= { hrSWInstalled 3 }

   hrSWInstalledEntry OBJECT-TYPE
       SYNTAX     HrSWInstalledEntry
       MAX-ACCESS not-accessible
       STATUS     current
       INDEX { hrSWInstalledIndex }
       ::= { hrSWInstalledTable 1 }

   HrSWInstalledEntry ::= SEQUENCE {
           hrSWInstalledIndex       Integer32,





           hrSWInstalledName        InternationalDisplayString,
           hrSWInstalledID          ProductID,
           hrSWInstalledType        INTEGER,
           hrSWInstalledDate        DateAndTime
   }

   hrSWInstalledIndex OBJECT-TYPE
       SYNTAX     Integer32 (1..2147483647)
       MAX-ACCESS read-only
       STATUS     current
       ::= { hrSWInstalledEntry 1 }

   hrSWInstalledName OBJECT-TYPE
       SYNTAX     InternationalDisplayString (SIZE (0..64))
       MAX-ACCESS read-only
       STATUS     current
       ::= { hrSWInstalledEntry 2 }

   hrSWInstalledID OBJECT-TYPE
       SYNTAX     ProductID
       MAX-ACCESS read-only
       STATUS     current
       ::= { hrSWInstalledEntry 3 }

   hrSWInstalledType OBJECT-TYPE
       SYNTAX     INTEGER {
                      unknown(1),
                      operatingSystem(2),
                      deviceDriver(3),
                      application(4)
                  }
       MAX-ACCESS read-only
       STATUS     current
       ::= { hrSWInstalledEntry 4 }





   hrSWInstalledDate OBJECT-TYPE
       SYNTAX     DateAndTime
       MAX-ACCESS read-only
       STATUS     current
       ::= { hrSWInstalledEntry 5 }


   hrMIBCompliances OBJECT IDENTIFIER ::= { hrMIBAdminInfo 2 }
   hrMIBGroups      OBJECT IDENTIFIER ::= { hrMIBAdminInfo 3 }

   hrMIBCompliance MODULE-COMPLIANCE
       STATUS current
       MODULE -- this module
         MANDATORY-GROUPS { hrSystemGroup, hrStorageGroup,
                            hrDeviceGroup }

         OBJECT hrSystemDate
             MIN-ACCESS read-only

         OBJECT hrSystemInitialLoadDevice
             MIN-ACCESS read-only

         OBJECT hrSystemInitialLoadParameters
             MIN-ACCESS read-only

         OBJECT hrStorageSize
             MIN-ACCESS read-only






         OBJECT hrFSLastFullBackupDate
             MIN-ACCESS read-only

         OBJECT hrFSLastPartialBackupDate
             MIN-ACCESS read-only

         GROUP hrSWRunGroup

         OBJECT hrSWRunStatus
             MIN-ACCESS read-only

         GROUP hrSWRunPerfGroup

         GROUP hrSWInstalledGroup

       ::= { hrMIBCompliances 1 }

       hrSystemGroup OBJECT-GROUP
           OBJECTS {
               hrSystemUptime, hrSystemDate,
               hrSystemInitialLoadDevice,
               hrSystemInitialLoadParameters,
               hrSystemNumUsers, hrSystemProcesses,
               hrSystemMaxProcesses
           }
           STATUS current
           ::= { hrMIBGroups 1 }






       hrStorageGroup OBJECT-GROUP
           OBJECTS {
               hrMemorySize, hrStorageIndex, hrStorageType,
               hrStorageDescr, hrStorageAllocationUnits,
               hrStorageSize, hrStorageUsed,
               hrStorageAllocationFailures
           }
           STATUS current
           ::= { hrMIBGroups 2 }

       hrDeviceGroup OBJECT-GROUP
           OBJECTS {
               hrDeviceIndex, hrDeviceType, hrDeviceDescr,
               hrDeviceID, hrDeviceStatus, hrDeviceErrors,
               hrProcessorFrwID, hrProcessorLoad,
               hrNetworkIfIndex, hrPrinterStatus,
               hrPrinterDetectedErrorState,
               hrDiskStorageAccess, hrDiskStorageMedia,
               hrDiskStorageRemoveble, hrDiskStorageCapacity,
               hrPartitionIndex, hrPartitionLabel,
               hrPartitionID, hrPartitionSize,
               hrPartitionFSIndex, hrFSIndex, hrFSMountPoint,
               hrFSRemoteMountPoint, hrFSType, hrFSAccess,
               hrFSBootable, hrFSStorageIndex,
               hrFSLastFullBackupDate,
               hrFSLastPartialBackupDate
           }
           STATUS current
           ::= { hrMIBGroups 3 }

       hrSWRunGroup OBJECT-GROUP
           OBJECTS {
               hrSWOSIndex, hrSWRunIndex, hrSWRunName,
               hrSWRunID, hrSWRunPath, hrSWRunParameters,
               hrSWRunType, hrSWRunStatus
           }
           STATUS current
           ::= { hrMIBGroups 4 }

       hrSWRunPerfGroup OBJECT-GROUP
           OBJECTS { hrSWRunPerfCPU, hrSWRunPerfMem }
           STATUS current





           ::= { hrMIBGroups 5 }

       hrSWInstalledGroup OBJECT-GROUP
           OBJECTS {
               hrSWInstalledLastChange,
               hrSWInstalledLastUpdateTime,
               hrSWInstalledIndex, hrSWInstalledName,
               hrSWInstalledID, hrSWInstalledType,
               hrSWInstalledDate
           }
           STATUS current
           ::= { hrMIBGroups 6 }

   END
   HOST-RESOURCES-TYPES DEFINITIONS ::= BEGIN

   IMPORTS
     MODULE-IDENTITY, OBJECT-IDENTITY        FROM SNMPv2-SMI
     hrMIBAdminInfo, hrStorage, hrDevice     FROM HOST-RESOURCES-MIB;

   hostResourcesTypesModule MODULE-IDENTITY
     LAST-UPDATED "200003060000Z"    -- 6 March, 2000
     ORGANIZATION "IETF Host Resources MIB Working Group"
     ::= { hrMIBAdminInfo 4 }

   hrStorageTypes          OBJECT IDENTIFIER ::= { hrStorage 1 }

   hrStorageOther OBJECT-IDENTITY
       STATUS current
       ::= { hrStorageTypes 1 }

   hrStorageRam OBJECT-IDENTITY
       STATUS current
       ::= { hrStorageTypes 2 }

   hrStorageVirtualMemory OBJECT-IDENTITY
       STATUS current
       ::= { hrStorageTypes 3 }

   hrStorageFixedDisk OBJECT-IDENTITY
       STATUS current
       ::= { hrStorageTypes 4 }

   hrStorageRemovableDisk OBJECT-IDENTITY
       STATUS current
       ::= { hrStorageTypes 5 }

   hrStorageFloppyDisk OBJECT-IDENTITY
       STATUS current
       ::= { hrStorageTypes 6 }

   hrStorageCompactDisc OBJECT-IDENTITY
       STATUS current
       ::= { hrStorageTypes 7 }

   hrStorageRamDisk OBJECT-IDENTITY
       STATUS current
       ::= { hrStorageTypes 8 }

   hrStorageFlashMemory OBJECT-IDENTITY
       STATUS current
       ::= { hrStorageTypes 9 }

   hrStorageNetworkDisk OBJECT-IDENTITY
       STATUS current
       ::= { hrStorageTypes 10 }

   hrDeviceTypes             OBJECT IDENTIFIER ::= { hrDevice 1 }

   hrDeviceOther OBJECT-IDENTITY
       STATUS current
       ::= { hrDeviceTypes 1 }

   hrDeviceUnknown OBJECT-IDENTITY
       STATUS current
       ::= { hrDeviceTypes 2 }






   hrDeviceProcessor OBJECT-IDENTITY
       STATUS current
       ::= { hrDeviceTypes 3 }

   hrDeviceNetwork OBJECT-IDENTITY
       STATUS current
       ::= { hrDeviceTypes 4 }

   hrDevicePrinter OBJECT-IDENTITY
       STATUS current
       ::= { hrDeviceTypes 5 }

   hrDeviceDiskStorage OBJECT-IDENTITY
       STATUS current
       ::= { hrDeviceTypes 6 }

   hrDeviceVideo OBJECT-IDENTITY
       STATUS current
       ::= { hrDeviceTypes 10 }

   hrDeviceAudio OBJECT-IDENTITY
       STATUS current
       ::= { hrDeviceTypes 11 }

   hrDeviceCoprocessor OBJECT-IDENTITY
       STATUS current
       ::= { hrDeviceTypes 12 }

   hrDeviceKeyboard OBJECT-IDENTITY
       STATUS current
       ::= { hrDeviceTypes 13 }






   hrDeviceModem OBJECT-IDENTITY
       STATUS current
       ::= { hrDeviceTypes 14 }

   hrDeviceParallelPort OBJECT-IDENTITY
       STATUS current
       ::= { hrDeviceTypes 15 }

   hrDevicePointing OBJECT-IDENTITY
       STATUS current
       ::= { hrDeviceTypes 16 }

   hrDeviceSerialPort OBJECT-IDENTITY
       STATUS current
       ::= { hrDeviceTypes 17 }

   hrDeviceTape OBJECT-IDENTITY
       STATUS current
       ::= { hrDeviceTypes 18 }

   hrDeviceClock OBJECT-IDENTITY
       STATUS current
       ::= { hrDeviceTypes 19 }

   hrDeviceVolatileMemory OBJECT-IDENTITY
       STATUS current
       ::= { hrDeviceTypes 20 }

   hrDeviceNonVolatileMemory OBJECT-IDENTITY
       STATUS current
       ::= { hrDeviceTypes 21 }

   hrFSTypes               OBJECT IDENTIFIER ::= { hrDevice 9 }

   hrFSOther OBJECT-IDENTITY
       STATUS  current
       ::= { hrFSTypes 1 }

   hrFSUnknown OBJECT-IDENTITY
       STATUS  current
       ::= { hrFSTypes 2 }

   hrFSBerkeleyFFS OBJECT-IDENTITY
       STATUS  current
       ::= { hrFSTypes 3 }

   hrFSSys5FS OBJECT-IDENTITY
       STATUS  current
       ::= { hrFSTypes 4 }

   hrFSFat OBJECT-IDENTITY
       STATUS  current
       ::= { hrFSTypes 5 }

   hrFSHPFS OBJECT-IDENTITY
       STATUS  current
       ::= { hrFSTypes 6 }





   hrFSHFS OBJECT-IDENTITY
       STATUS  current
       ::= { hrFSTypes 7 }

   hrFSMFS OBJECT-IDENTITY
       STATUS  current
       ::= { hrFSTypes 8 }

   hrFSNTFS OBJECT-IDENTITY
       STATUS  current
       ::= { hrFSTypes 9 }

   hrFSVNode OBJECT-IDENTITY
       STATUS  current
       ::= { hrFSTypes 10 }

   hrFSJournaled OBJECT-IDENTITY
       STATUS  current
       ::= { hrFSTypes 11 }

   hrFSiso9660 OBJECT-IDENTITY
       STATUS  current
       ::= { hrFSTypes 12 }

   hrFSRockRidge OBJECT-IDENTITY
       STATUS  current
       ::= { hrFSTypes 13 }





   hrFSNFS OBJECT-IDENTITY
       STATUS  current
       ::= { hrFSTypes 14 }

   hrFSNetware OBJECT-IDENTITY
       STATUS  current
       ::= { hrFSTypes 15 }

   hrFSAFS OBJECT-IDENTITY
       STATUS  current
       ::= { hrFSTypes 16 }

   hrFSDFS OBJECT-IDENTITY
       STATUS  current
       ::= { hrFSTypes 17 }

   hrFSAppleshare OBJECT-IDENTITY
       STATUS  current
       ::= { hrFSTypes 18 }

   hrFSRFS OBJECT-IDENTITY
       STATUS  current
       ::= { hrFSTypes 19 }

   hrFSDGCFS OBJECT-IDENTITY
       STATUS  current
       ::= { hrFSTypes 20 }





   hrFSBFS OBJECT-IDENTITY
       STATUS  current
       ::= { hrFSTypes 21 }

   hrFSFAT32 OBJECT-IDENTITY
       STATUS  current
       ::= { hrFSTypes 22 }

   hrFSLinuxExt2 OBJECT-IDENTITY
       STATUS  current
       ::= { hrFSTypes 23 }

   END
