RADIUS-ACC-SERVER-MIB DEFINITIONS ::= BEGIN

   IMPORTS
          MODULE-IDENTITY, OBJECT-TYPE, OBJECT-IDENTITY,
          Counter32, Integer32,
          IpAddress, TimeTicks, mib-2      FROM SNMPv2-SMI
          SnmpAdminString                  FROM SNMP-FRAMEWORK-MIB
          InetAddressType, InetAddress     FROM INET-ADDRESS-MIB
          MODULE-COMPLIANCE, OBJECT-GROUP  FROM SNMPv2-CONF;

   radiusAccServMIB MODULE-IDENTITY
          LAST-UPDATED "200608210000Z"  -- 21 August 2006
          ORGANIZATION "IETF RADIUS Extensions Working Group."
          ::= { radiusAccounting 1 }

   radiusMIB  OBJECT-IDENTITY
          STATUS  current
          ::= { mib-2 67 }

   radiusAccounting  OBJECT IDENTIFIER ::= {radiusMIB 2}

   radiusAccServMIBObjects  OBJECT IDENTIFIER
         ::= { radiusAccServMIB 1 }

   radiusAccServ  OBJECT IDENTIFIER
         ::= { radiusAccServMIBObjects 1 }

   radiusAccServIdent OBJECT-TYPE
          SYNTAX      SnmpAdminString
          MAX-ACCESS  read-only
          STATUS      current
          ::= {radiusAccServ 1}

   radiusAccServUpTime OBJECT-TYPE
          SYNTAX      TimeTicks
          MAX-ACCESS  read-only





          STATUS      current
          ::= {radiusAccServ 2}

   radiusAccServResetTime OBJECT-TYPE
          SYNTAX      TimeTicks
          MAX-ACCESS  read-only
          STATUS      current
          ::= {radiusAccServ 3}

   radiusAccServConfigReset OBJECT-TYPE
          SYNTAX INTEGER { other(1),
                           reset(2),
                           initializing(3),
                           running(4)}
          MAX-ACCESS  read-write
          STATUS      current
          ::= {radiusAccServ 4}

   radiusAccServTotalRequests OBJECT-TYPE
          SYNTAX Counter32
          UNITS "packets"
          MAX-ACCESS read-only
          STATUS current
          ::= { radiusAccServ 5 }

   radiusAccServTotalInvalidRequests OBJECT-TYPE
          SYNTAX Counter32
          UNITS "packets"
          MAX-ACCESS read-only
          STATUS current
          ::= { radiusAccServ 6 }

   radiusAccServTotalDupRequests OBJECT-TYPE
          SYNTAX Counter32
          UNITS "packets"
          MAX-ACCESS read-only
          STATUS current
          ::= { radiusAccServ 7 }

   radiusAccServTotalResponses OBJECT-TYPE
          SYNTAX Counter32
          UNITS "packets"
          MAX-ACCESS read-only
          STATUS current
          ::= { radiusAccServ 8 }

   radiusAccServTotalMalformedRequests OBJECT-TYPE
          SYNTAX Counter32
          UNITS "packets"
          MAX-ACCESS read-only
          STATUS current





          ::= { radiusAccServ 9 }

   radiusAccServTotalBadAuthenticators OBJECT-TYPE
         SYNTAX Counter32
         UNITS "packets"
         MAX-ACCESS read-only
         STATUS current
         ::= { radiusAccServ 10 }

   radiusAccServTotalPacketsDropped OBJECT-TYPE
         SYNTAX Counter32
         UNITS "packets"
         MAX-ACCESS read-only
         STATUS current
         ::= { radiusAccServ 11 }

   radiusAccServTotalNoRecords OBJECT-TYPE
          SYNTAX Counter32
          UNITS "packets"
          MAX-ACCESS read-only
          STATUS current
          ::= { radiusAccServ 12 }

   radiusAccServTotalUnknownTypes OBJECT-TYPE
         SYNTAX Counter32
         UNITS "packets"
         MAX-ACCESS read-only
         STATUS current
         ::= { radiusAccServ 13 }

   radiusAccClientTable OBJECT-TYPE





          SYNTAX     SEQUENCE OF RadiusAccClientEntry
          MAX-ACCESS not-accessible
          STATUS     deprecated
          ::= { radiusAccServ 14 }

   radiusAccClientEntry OBJECT-TYPE
          SYNTAX     RadiusAccClientEntry
          MAX-ACCESS not-accessible
          STATUS     deprecated
          INDEX      { radiusAccClientIndex }
          ::= { radiusAccClientTable 1 }

   RadiusAccClientEntry ::= SEQUENCE {
          radiusAccClientIndex                           Integer32,
          radiusAccClientAddress                         IpAddress,
          radiusAccClientID                        SnmpAdminString,
          radiusAccServPacketsDropped                    Counter32,
          radiusAccServRequests                          Counter32,
          radiusAccServDupRequests                       Counter32,
          radiusAccServResponses                         Counter32,
          radiusAccServBadAuthenticators                 Counter32,
          radiusAccServMalformedRequests                 Counter32,
          radiusAccServNoRecords                         Counter32,
          radiusAccServUnknownTypes                      Counter32
   }

   radiusAccClientIndex OBJECT-TYPE
          SYNTAX     Integer32 (1..2147483647)
          MAX-ACCESS not-accessible
          STATUS     deprecated
          ::= { radiusAccClientEntry 1 }

   radiusAccClientAddress OBJECT-TYPE
          SYNTAX     IpAddress
          MAX-ACCESS read-only
          STATUS     deprecated
          ::= { radiusAccClientEntry 2 }

   radiusAccClientID OBJECT-TYPE
          SYNTAX     SnmpAdminString
          MAX-ACCESS read-only
          STATUS     deprecated
          ::= { radiusAccClientEntry 3 }


   radiusAccServPacketsDropped OBJECT-TYPE
         SYNTAX Counter32
         UNITS "packets"
         MAX-ACCESS read-only
         STATUS deprecated
        ::= { radiusAccClientEntry  4 }

   radiusAccServRequests OBJECT-TYPE
          SYNTAX Counter32
          UNITS "packets"
          MAX-ACCESS read-only
          STATUS deprecated
          ::= { radiusAccClientEntry  5 }

   radiusAccServDupRequests OBJECT-TYPE
          SYNTAX Counter32





          UNITS "packets"
          MAX-ACCESS read-only
          STATUS deprecated
          ::= { radiusAccClientEntry 6 }

   radiusAccServResponses OBJECT-TYPE
          SYNTAX Counter32
          UNITS "packets"
          MAX-ACCESS read-only
          STATUS deprecated
          ::= { radiusAccClientEntry  7 }

   radiusAccServBadAuthenticators OBJECT-TYPE
          SYNTAX Counter32
          UNITS "packets"
          MAX-ACCESS read-only
          STATUS deprecated
          ::= { radiusAccClientEntry  8 }

   radiusAccServMalformedRequests OBJECT-TYPE
          SYNTAX Counter32
          UNITS "packets"
          MAX-ACCESS read-only
          STATUS deprecated
          ::= { radiusAccClientEntry  9 }

   radiusAccServNoRecords OBJECT-TYPE
          SYNTAX Counter32
          UNITS "packets"





          MAX-ACCESS read-only
          STATUS deprecated
          ::= { radiusAccClientEntry  10 }

   radiusAccServUnknownTypes OBJECT-TYPE
          SYNTAX Counter32
          UNITS "packets"
          MAX-ACCESS read-only
          STATUS deprecated
          ::= { radiusAccClientEntry  11 }



   radiusAccClientExtTable OBJECT-TYPE
          SYNTAX     SEQUENCE OF RadiusAccClientExtEntry
          MAX-ACCESS not-accessible
          STATUS     current
          ::= { radiusAccServ 15 }

   radiusAccClientExtEntry OBJECT-TYPE
          SYNTAX     RadiusAccClientExtEntry
          MAX-ACCESS not-accessible
          STATUS     current
          INDEX      { radiusAccClientExtIndex }
          ::= { radiusAccClientExtTable 1 }

   RadiusAccClientExtEntry ::= SEQUENCE {
          radiusAccClientExtIndex               Integer32,
          radiusAccClientInetAddressType        InetAddressType,
          radiusAccClientInetAddress            InetAddress,
          radiusAccClientExtID                  SnmpAdminString,
          radiusAccServExtPacketsDropped        Counter32,





          radiusAccServExtRequests              Counter32,
          radiusAccServExtDupRequests           Counter32,
          radiusAccServExtResponses             Counter32,
          radiusAccServExtBadAuthenticators     Counter32,
          radiusAccServExtMalformedRequests     Counter32,
          radiusAccServExtNoRecords             Counter32,
          radiusAccServExtUnknownTypes          Counter32,
          radiusAccServerCounterDiscontinuity   TimeTicks
   }

   radiusAccClientExtIndex OBJECT-TYPE
          SYNTAX     Integer32 (1..2147483647)
          MAX-ACCESS not-accessible
          STATUS     current
          ::= { radiusAccClientExtEntry 1 }

          radiusAccClientInetAddressType OBJECT-TYPE
            SYNTAX     InetAddressType
            MAX-ACCESS read-only
            STATUS     current
            ::= { radiusAccClientExtEntry 2 }

      radiusAccClientInetAddress OBJECT-TYPE
            SYNTAX     InetAddress
            MAX-ACCESS read-only
            STATUS     current
            ::= { radiusAccClientExtEntry 3 }

   radiusAccClientExtID OBJECT-TYPE
          SYNTAX     SnmpAdminString
          MAX-ACCESS read-only
          STATUS     current
          ::= { radiusAccClientExtEntry 4 }






   radiusAccServExtPacketsDropped OBJECT-TYPE
         SYNTAX Counter32
         UNITS "packets"
         MAX-ACCESS read-only
         STATUS current
        ::= { radiusAccClientExtEntry  5 }

   radiusAccServExtRequests OBJECT-TYPE
          SYNTAX Counter32
          UNITS "packets"
          MAX-ACCESS read-only
          STATUS current
          ::= { radiusAccClientExtEntry  6 }

   radiusAccServExtDupRequests OBJECT-TYPE
          SYNTAX Counter32
          UNITS "packets"
          MAX-ACCESS read-only
          STATUS current
          ::= { radiusAccClientExtEntry 7 }

   radiusAccServExtResponses OBJECT-TYPE
          SYNTAX Counter32
          UNITS "packets"
          MAX-ACCESS read-only
          STATUS current
          ::= { radiusAccClientExtEntry  8 }

   radiusAccServExtBadAuthenticators OBJECT-TYPE
          SYNTAX Counter32
          UNITS "packets"
          MAX-ACCESS read-only
          STATUS current
          ::= { radiusAccClientExtEntry  9 }

   radiusAccServExtMalformedRequests OBJECT-TYPE
          SYNTAX Counter32
          UNITS "packets"
          MAX-ACCESS read-only
          STATUS current
          ::= { radiusAccClientExtEntry  10 }

   radiusAccServExtNoRecords OBJECT-TYPE
          SYNTAX Counter32
          UNITS "packets"
          MAX-ACCESS read-only
          STATUS current
          ::= { radiusAccClientExtEntry  11 }

   radiusAccServExtUnknownTypes OBJECT-TYPE
          SYNTAX Counter32
          UNITS "packets"
          MAX-ACCESS read-only
          STATUS current
          ::= { radiusAccClientExtEntry  12 }

   radiusAccServerCounterDiscontinuity OBJECT-TYPE
            SYNTAX TimeTicks
            UNITS "centiseconds"
            MAX-ACCESS read-only
            STATUS current
            ::= { radiusAccClientExtEntry 13 }



   radiusAccServMIBConformance  OBJECT IDENTIFIER
          ::= { radiusAccServMIB 2 }

   radiusAccServMIBCompliances  OBJECT IDENTIFIER
          ::= { radiusAccServMIBConformance 1 }

   radiusAccServMIBGroups  OBJECT IDENTIFIER
          ::= { radiusAccServMIBConformance 2 }



   radiusAccServMIBCompliance MODULE-COMPLIANCE
          STATUS  deprecated
          MODULE  -- this module
          MANDATORY-GROUPS { radiusAccServMIBGroup }

          OBJECT        radiusAccServConfigReset
          WRITE-SYNTAX  INTEGER { reset(2) }

          ::= { radiusAccServMIBCompliances 1 }

   radiusAccServExtMIBCompliance MODULE-COMPLIANCE
          STATUS  current
          MODULE  -- this module
          MANDATORY-GROUPS { radiusAccServExtMIBGroup }

          OBJECT        radiusAccServConfigReset
          WRITE-SYNTAX  INTEGER { reset(2) }






          OBJECT radiusAccClientInetAddressType
           SYNTAX InetAddressType { ipv4(1), ipv6(2) }

           OBJECT radiusAccClientInetAddress
           SYNTAX InetAddress ( SIZE (4|16) )

          ::= { radiusAccServMIBCompliances 2 }



   radiusAccServMIBGroup OBJECT-GROUP
         OBJECTS {radiusAccServIdent,
                  radiusAccServUpTime,
                  radiusAccServResetTime,
                  radiusAccServConfigReset,
                  radiusAccServTotalRequests,
                  radiusAccServTotalInvalidRequests,
                  radiusAccServTotalDupRequests,
                  radiusAccServTotalResponses,
                  radiusAccServTotalMalformedRequests,
                  radiusAccServTotalBadAuthenticators,
                  radiusAccServTotalPacketsDropped,
                  radiusAccServTotalNoRecords,
                  radiusAccServTotalUnknownTypes,
                  radiusAccClientAddress,
                  radiusAccClientID,
                  radiusAccServPacketsDropped,
                  radiusAccServRequests,
                  radiusAccServDupRequests,
                  radiusAccServResponses,
                  radiusAccServBadAuthenticators,
                  radiusAccServMalformedRequests,
                  radiusAccServNoRecords,
                  radiusAccServUnknownTypes
                 }
         STATUS  deprecated





         ::= { radiusAccServMIBGroups 1 }

   radiusAccServExtMIBGroup OBJECT-GROUP
         OBJECTS {radiusAccServIdent,
                  radiusAccServUpTime,
                  radiusAccServResetTime,
                  radiusAccServConfigReset,
                  radiusAccServTotalRequests,
                  radiusAccServTotalInvalidRequests,
                  radiusAccServTotalDupRequests,
                  radiusAccServTotalResponses,
                  radiusAccServTotalMalformedRequests,
                  radiusAccServTotalBadAuthenticators,
                  radiusAccServTotalPacketsDropped,
                  radiusAccServTotalNoRecords,
                  radiusAccServTotalUnknownTypes,
                  radiusAccClientInetAddressType,
                  radiusAccClientInetAddress,
                  radiusAccClientExtID,
                  radiusAccServExtPacketsDropped,
                  radiusAccServExtRequests,
                  radiusAccServExtDupRequests,
                  radiusAccServExtResponses,
                  radiusAccServExtBadAuthenticators,
                  radiusAccServExtMalformedRequests,
                  radiusAccServExtNoRecords,
                  radiusAccServExtUnknownTypes,
                  radiusAccServerCounterDiscontinuity
                 }
         STATUS  current
         ::= { radiusAccServMIBGroups 2 }

   END
