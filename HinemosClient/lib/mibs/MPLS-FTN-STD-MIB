MPLS-FTN-STD-MIB DEFINITIONS ::= BEGIN

   IMPORTS
      MODULE-IDENTITY, OBJECT-TYPE, Unsigned32, Counter64, Integer32
          FROM SNMPv2-SMI                                   -- [RFC2578]
      RowStatus, StorageType, RowPointer,
      TEXTUAL-CONVENTION, TimeStamp
          FROM SNMPv2-TC                                    -- [RFC2579]
      MODULE-COMPLIANCE, OBJECT-GROUP
          FROM SNMPv2-CONF                                  -- [RFC2580]
      InterfaceIndexOrZero,
      ifGeneralInformationGroup, ifCounterDiscontinuityGroup
          FROM IF-MIB                                       -- [RFC2863]
      SnmpAdminString
          FROM SNMP-FRAMEWORK-MIB                           -- [RFC3411]
      Dscp
          FROM DIFFSERV-DSCP-TC                             -- [RFC3289]
      InetAddressType, InetAddress, InetPortNumber
          FROM INET-ADDRESS-MIB                             -- [RFC3291]
      mplsStdMIB
          FROM MPLS-TC-STD-MIB                              -- [RFC3811]





      ;

   mplsFTNStdMIB MODULE-IDENTITY
      LAST-UPDATED "200406030000Z"  -- June 6, 2004
      ORGANIZATION "Multiprotocol Label Switching (MPLS) Working Group"









       ::= { mplsStdMIB 8 }

   MplsFTNEntryIndex ::= TEXTUAL-CONVENTION
      STATUS              current
      SYNTAX              Unsigned32 (1..4294967295)

   MplsFTNEntryIndexOrZero ::= TEXTUAL-CONVENTION
      STATUS              current
      SYNTAX              Unsigned32 (0..4294967295)


   mplsFTNNotifications OBJECT IDENTIFIER ::= { mplsFTNStdMIB 0 }
   mplsFTNObjects       OBJECT IDENTIFIER ::= { mplsFTNStdMIB 1 }
   mplsFTNConformance   OBJECT IDENTIFIER ::= { mplsFTNStdMIB 2 }

   mplsFTNIndexNext OBJECT-TYPE
      SYNTAX              MplsFTNEntryIndexOrZero
      MAX-ACCESS          read-only
      STATUS              current
      ::= { mplsFTNObjects 1 }

   mplsFTNTableLastChanged OBJECT-TYPE
      SYNTAX              TimeStamp
      MAX-ACCESS          read-only
      STATUS              current
      ::=  { mplsFTNObjects 2 }

   mplsFTNTable  OBJECT-TYPE
      SYNTAX          SEQUENCE OF MplsFTNEntry
      MAX-ACCESS      not-accessible
      STATUS          current
      ::=  { mplsFTNObjects 3 }

   mplsFTNEntry  OBJECT-TYPE
      SYNTAX          MplsFTNEntry
      MAX-ACCESS      not-accessible
      STATUS          current
      INDEX { mplsFTNIndex }
      ::=  { mplsFTNTable 1 }

   MplsFTNEntry  ::=  SEQUENCE {
         mplsFTNIndex               MplsFTNEntryIndex,
         mplsFTNRowStatus           RowStatus,
         mplsFTNDescr               SnmpAdminString,
         mplsFTNMask                BITS,
         mplsFTNAddrType            InetAddressType,
         mplsFTNSourceAddrMin       InetAddress,
         mplsFTNSourceAddrMax       InetAddress,





         mplsFTNDestAddrMin         InetAddress,
         mplsFTNDestAddrMax         InetAddress,
         mplsFTNSourcePortMin       InetPortNumber,
         mplsFTNSourcePortMax       InetPortNumber,
         mplsFTNDestPortMin         InetPortNumber,
         mplsFTNDestPortMax         InetPortNumber,
         mplsFTNProtocol            Integer32,
         mplsFTNDscp                Dscp,
         mplsFTNActionType          INTEGER,
         mplsFTNActionPointer       RowPointer,
         mplsFTNStorageType         StorageType
      }

   mplsFTNIndex   OBJECT-TYPE
      SYNTAX              MplsFTNEntryIndex
      MAX-ACCESS          not-accessible
      STATUS              current
      ::= { mplsFTNEntry 1 }

   mplsFTNRowStatus OBJECT-TYPE
      SYNTAX              RowStatus
      MAX-ACCESS          read-create
      STATUS              current
      ::= { mplsFTNEntry 2 }

   mplsFTNDescr   OBJECT-TYPE
      SYNTAX              SnmpAdminString
      MAX-ACCESS          read-create
      STATUS              current





      ::= { mplsFTNEntry 3 }

   mplsFTNMask OBJECT-TYPE
      SYNTAX             BITS {
                          sourceAddr(0),
                          destAddr(1),
                          sourcePort(2),
                          destPort(3),
                          protocol(4),
                          dscp(5)
                         }
      MAX-ACCESS          read-create
      STATUS              current
      ::= { mplsFTNEntry 4 }

   mplsFTNAddrType OBJECT-TYPE
      SYNTAX             InetAddressType
      MAX-ACCESS         read-create
      STATUS             current
      ::= { mplsFTNEntry 5 }

   mplsFTNSourceAddrMin OBJECT-TYPE
      SYNTAX             InetAddress
      MAX-ACCESS         read-create
      STATUS             current
      ::= { mplsFTNEntry 6 }

   mplsFTNSourceAddrMax OBJECT-TYPE
      SYNTAX             InetAddress
      MAX-ACCESS         read-create
      STATUS             current
      ::= { mplsFTNEntry 7 }

   mplsFTNDestAddrMin OBJECT-TYPE
      SYNTAX             InetAddress
      MAX-ACCESS         read-create
      STATUS             current
      ::= { mplsFTNEntry 8 }

   mplsFTNDestAddrMax OBJECT-TYPE
      SYNTAX             InetAddress
      MAX-ACCESS         read-create
      STATUS             current
      ::= { mplsFTNEntry 9 }

   mplsFTNSourcePortMin OBJECT-TYPE
      SYNTAX             InetPortNumber
      MAX-ACCESS         read-create
      STATUS             current
      DEFVAL { 0 }
      ::= { mplsFTNEntry 10 }

   mplsFTNSourcePortMax OBJECT-TYPE
      SYNTAX             InetPortNumber
      MAX-ACCESS         read-create
      STATUS             current
      DEFVAL { 65535 }
      ::= { mplsFTNEntry 11 }

   mplsFTNDestPortMin OBJECT-TYPE
      SYNTAX             InetPortNumber
      MAX-ACCESS         read-create
      STATUS             current
      DEFVAL { 0 }
      ::= { mplsFTNEntry 12 }

   mplsFTNDestPortMax OBJECT-TYPE
      SYNTAX             InetPortNumber
      MAX-ACCESS         read-create
      STATUS             current
      DEFVAL { 65535 }
      ::= { mplsFTNEntry 13 }

   mplsFTNProtocol OBJECT-TYPE
      SYNTAX             Integer32 (0..255)
      MAX-ACCESS         read-create
      STATUS             current
      DEFVAL { 255 }
      ::= { mplsFTNEntry 14 }

   mplsFTNDscp OBJECT-TYPE
      SYNTAX             Dscp
      MAX-ACCESS         read-create
      STATUS             current





      ::= { mplsFTNEntry 15 }

   mplsFTNActionType OBJECT-TYPE
      SYNTAX    INTEGER {
                   redirectLsp(1),   -- redirect into LSP
                   redirectTunnel(2) -- redirect into tunnel
                }
      MAX-ACCESS         read-create
      STATUS             current
      ::= { mplsFTNEntry 16 }

   mplsFTNActionPointer OBJECT-TYPE
      SYNTAX             RowPointer
      MAX-ACCESS         read-create
      STATUS             current
      ::= { mplsFTNEntry 17 }






   mplsFTNStorageType OBJECT-TYPE
      SYNTAX             StorageType
      MAX-ACCESS         read-create
      STATUS             current
      DEFVAL { nonVolatile }
      ::= { mplsFTNEntry 18 }



   mplsFTNMapTableLastChanged OBJECT-TYPE
      SYNTAX              TimeStamp
      MAX-ACCESS          read-only
      STATUS              current
      ::=  { mplsFTNObjects 4 }


   mplsFTNMapTable OBJECT-TYPE
      SYNTAX              SEQUENCE OF MplsFTNMapEntry
      MAX-ACCESS          not-accessible
      STATUS              current
      ::=  { mplsFTNObjects 5 }

   mplsFTNMapEntry OBJECT-TYPE
      SYNTAX              MplsFTNMapEntry
      MAX-ACCESS          not-accessible
      STATUS              current
      INDEX {
            mplsFTNMapIndex,
            mplsFTNMapPrevIndex,
            mplsFTNMapCurrIndex
      }
      ::=  { mplsFTNMapTable 1 }

   MplsFTNMapEntry  ::=  SEQUENCE {





         mplsFTNMapIndex       InterfaceIndexOrZero,
         mplsFTNMapPrevIndex    MplsFTNEntryIndexOrZero,
         mplsFTNMapCurrIndex    MplsFTNEntryIndex,
         mplsFTNMapRowStatus    RowStatus,
         mplsFTNMapStorageType  StorageType
      }

   mplsFTNMapIndex OBJECT-TYPE
      SYNTAX              InterfaceIndexOrZero
      MAX-ACCESS          not-accessible
      STATUS              current
      ::= { mplsFTNMapEntry 1 }

   mplsFTNMapPrevIndex OBJECT-TYPE
      SYNTAX              MplsFTNEntryIndexOrZero
      MAX-ACCESS          not-accessible
      STATUS              current
      ::=  { mplsFTNMapEntry 2 }

   mplsFTNMapCurrIndex OBJECT-TYPE
      SYNTAX              MplsFTNEntryIndex
      MAX-ACCESS          not-accessible
      STATUS              current
      ::=  { mplsFTNMapEntry 3 }

   mplsFTNMapRowStatus OBJECT-TYPE
      SYNTAX              RowStatus {
                                active(1),
                                createAndGo(4),
                                destroy(6)
                             }
      MAX-ACCESS          read-create
      STATUS              current





      ::=  { mplsFTNMapEntry 4 }

   mplsFTNMapStorageType OBJECT-TYPE
      SYNTAX              StorageType
      MAX-ACCESS          read-create
      STATUS              current
      DEFVAL { nonVolatile }
      ::= { mplsFTNMapEntry 5 }



   mplsFTNPerfTable OBJECT-TYPE
      SYNTAX              SEQUENCE OF MplsFTNPerfEntry
      MAX-ACCESS          not-accessible
      STATUS              current
      ::= { mplsFTNObjects 6 }

   mplsFTNPerfEntry OBJECT-TYPE
      SYNTAX              MplsFTNPerfEntry
      MAX-ACCESS          not-accessible
      STATUS              current
      INDEX  { mplsFTNPerfIndex, mplsFTNPerfCurrIndex }
      ::=  { mplsFTNPerfTable 1 }






   MplsFTNPerfEntry  ::=  SEQUENCE {
         mplsFTNPerfIndex                     InterfaceIndexOrZero,
         mplsFTNPerfCurrIndex                 MplsFTNEntryIndex,
         mplsFTNPerfMatchedPackets            Counter64,
         mplsFTNPerfMatchedOctets             Counter64,
         mplsFTNPerfDiscontinuityTime         TimeStamp
      }

   mplsFTNPerfIndex OBJECT-TYPE
      SYNTAX              InterfaceIndexOrZero
      MAX-ACCESS          not-accessible
      STATUS              current
      ::= { mplsFTNPerfEntry 1 }

   mplsFTNPerfCurrIndex OBJECT-TYPE
      SYNTAX              MplsFTNEntryIndex
      MAX-ACCESS          not-accessible
      STATUS              current
      ::=  { mplsFTNPerfEntry 2 }

   mplsFTNPerfMatchedPackets OBJECT-TYPE
      SYNTAX              Counter64
      MAX-ACCESS          read-only
      STATUS              current
      ::= { mplsFTNPerfEntry 3 }

   mplsFTNPerfMatchedOctets OBJECT-TYPE
      SYNTAX              Counter64
      MAX-ACCESS          read-only
      STATUS              current
      ::= { mplsFTNPerfEntry 4 }

   mplsFTNPerfDiscontinuityTime OBJECT-TYPE
      SYNTAX              TimeStamp
      MAX-ACCESS          read-only
      STATUS              current
      ::= { mplsFTNPerfEntry 5 }




   mplsFTNGroups
      OBJECT IDENTIFIER ::= { mplsFTNConformance 1 }
   mplsFTNCompliances
      OBJECT IDENTIFIER ::= { mplsFTNConformance 2 }

   mplsFTNModuleFullCompliance MODULE-COMPLIANCE
      STATUS current

      MODULE IF-MIB -- The Interfaces Group MIB, RFC 2863.
      MANDATORY-GROUPS {
         ifGeneralInformationGroup,
         ifCounterDiscontinuityGroup
      }

      MODULE -- This module.
      MANDATORY-GROUPS {
         mplsFTNRuleGroup,
         mplsFTNMapGroup,
         mplsFTNPerfGroup





      }

      OBJECT mplsFTNAddrType
      SYNTAX InetAddressType { ipv4(1), ipv6(2) }

      OBJECT mplsFTNSourceAddrMin
      SYNTAX       InetAddress (SIZE (4 | 20))

      OBJECT mplsFTNSourceAddrMax
      SYNTAX       InetAddress (SIZE (4 | 20))

      OBJECT mplsFTNDestAddrMin
      SYNTAX       InetAddress (SIZE (4 | 20))

      OBJECT mplsFTNDestAddrMax
      SYNTAX       InetAddress (SIZE (4 | 20))
      ::= { mplsFTNCompliances 1 }

   mplsFTNModuleReadOnlyCompliance MODULE-COMPLIANCE
      STATUS current

      MODULE IF-MIB -- The interfaces Group MIB, RFC 2863
      MANDATORY-GROUPS {
         ifGeneralInformationGroup,
         ifCounterDiscontinuityGroup
      }

      MODULE -- This module
      MANDATORY-GROUPS {
         mplsFTNRuleGroup,
         mplsFTNMapGroup,
         mplsFTNPerfGroup
      }

      OBJECT mplsFTNIndexNext
      MIN-ACCESS   not-accessible

      OBJECT mplsFTNRowStatus
      SYNTAX       RowStatus { active(1) }
      MIN-ACCESS   read-only

      OBJECT mplsFTNDescr
      MIN-ACCESS   read-only

      OBJECT mplsFTNMask
      MIN-ACCESS   read-only

      OBJECT mplsFTNAddrType
      SYNTAX       InetAddressType { ipv4(1), ipv6(2) }
      MIN-ACCESS   read-only

      OBJECT mplsFTNSourceAddrMin





      SYNTAX       InetAddress (SIZE (4 | 20))
      MIN-ACCESS   read-only

      OBJECT mplsFTNSourceAddrMax
      SYNTAX       InetAddress (SIZE (4 | 20))
      MIN-ACCESS   read-only

      OBJECT mplsFTNDestAddrMin
      SYNTAX       InetAddress (SIZE (4 | 20))
      MIN-ACCESS   read-only

      OBJECT mplsFTNDestAddrMax
      SYNTAX       InetAddress (SIZE (4 | 20))
      MIN-ACCESS   read-only

      OBJECT mplsFTNSourcePortMin
      MIN-ACCESS   read-only

      OBJECT mplsFTNSourcePortMax
      MIN-ACCESS   read-only

      OBJECT mplsFTNDestPortMin
      MIN-ACCESS   read-only

      OBJECT mplsFTNDestPortMax
      MIN-ACCESS   read-only

      OBJECT mplsFTNProtocol





      MIN-ACCESS   read-only

      OBJECT mplsFTNActionType
      MIN-ACCESS   read-only

      OBJECT mplsFTNActionPointer
      MIN-ACCESS   read-only

      OBJECT mplsFTNDscp
      MIN-ACCESS   read-only

      OBJECT mplsFTNStorageType
      MIN-ACCESS   read-only

      OBJECT mplsFTNMapRowStatus
      SYNTAX       RowStatus { active(1) }
      MIN-ACCESS   read-only

      OBJECT mplsFTNMapStorageType
      MIN-ACCESS   read-only
      ::= { mplsFTNCompliances 2 }

   mplsFTNRuleGroup OBJECT-GROUP
      OBJECTS {
            mplsFTNIndexNext,
            mplsFTNTableLastChanged,
            mplsFTNRowStatus,
            mplsFTNDescr,
            mplsFTNMask,
            mplsFTNAddrType,
            mplsFTNSourceAddrMin,
            mplsFTNSourceAddrMax,





            mplsFTNDestAddrMin,
            mplsFTNDestAddrMax,
            mplsFTNSourcePortMin,
            mplsFTNSourcePortMax,
            mplsFTNDestPortMin,
            mplsFTNDestPortMax,
            mplsFTNProtocol,
            mplsFTNActionType,
            mplsFTNActionPointer,
            mplsFTNDscp,
            mplsFTNStorageType
      }
      STATUS current
      ::= { mplsFTNGroups 1 }

   mplsFTNMapGroup OBJECT-GROUP
      OBJECTS {
            mplsFTNMapTableLastChanged,
            mplsFTNMapRowStatus,
            mplsFTNMapStorageType
      }
      STATUS current
      ::= { mplsFTNGroups 2 }

   mplsFTNPerfGroup OBJECT-GROUP
      OBJECTS {
            mplsFTNPerfMatchedPackets,
            mplsFTNPerfMatchedOctets,
            mplsFTNPerfDiscontinuityTime
      }
      STATUS current
      ::= { mplsFTNGroups 3 }

   END
