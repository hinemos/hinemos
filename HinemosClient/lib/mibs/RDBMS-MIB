RDBMS-MIB DEFINITIONS ::= BEGIN

  IMPORTS
     MODULE-IDENTITY, OBJECT-TYPE, NOTIFICATION-TYPE,
      Counter32, Gauge32, Integer32
      , OBJECT-IDENTITY
          FROM SNMPv2-SMI
   MODULE-COMPLIANCE, OBJECT-GROUP
        FROM SNMPv2-CONF
      DisplayString, DateAndTime, AutonomousType
          FROM SNMPv2-TC
      applIndex, applGroups
          FROM NETWORK-SERVICES-MIB
      mib-2
          FROM RFC1213-MIB;

  rdbmsMIB MODULE-IDENTITY
      LAST-UPDATED "9406150655Z"
      ORGANIZATION "IETF RDBMSMIB Working Group"

      ::= { mib-2 39 }

  rdbmsObjects        OBJECT IDENTIFIER ::= { rdbmsMIB 1 }


  rdbmsDbTable    OBJECT-TYPE
      SYNTAX      SEQUENCE OF RdbmsDbEntry
      MAX-ACCESS  not-accessible
      STATUS      current
      ::= { rdbmsObjects 1 }






  rdbmsDbEntry    OBJECT-TYPE
      SYNTAX      RdbmsDbEntry
      MAX-ACCESS  not-accessible
      STATUS      current
      INDEX  { rdbmsDbIndex }
      ::= { rdbmsDbTable 1 }

  RdbmsDbEntry    ::=
      SEQUENCE {
          rdbmsDbIndex            INTEGER,
          rdbmsDbPrivateMibOID        OBJECT IDENTIFIER,
          rdbmsDbVendorName       DisplayString,
          rdbmsDbName             DisplayString,
          rdbmsDbContact          DisplayString
      }

  rdbmsDbIndex        OBJECT-TYPE
      SYNTAX          INTEGER (1..2147483647)
      MAX-ACCESS      not-accessible
      STATUS          current
      ::= { rdbmsDbEntry  1 }

  rdbmsDbPrivateMibOID    OBJECT-TYPE
      SYNTAX          OBJECT IDENTIFIER
      MAX-ACCESS      read-only
      STATUS          current
      ::= { rdbmsDbEntry  2 }

  rdbmsDbVendorName   OBJECT-TYPE
      SYNTAX          DisplayString
      MAX-ACCESS      read-only
      STATUS          current
      ::= { rdbmsDbEntry 3 }

  rdbmsDbName     OBJECT-TYPE
      SYNTAX      DisplayString
      MAX-ACCESS  read-only
      STATUS      current
      ::= { rdbmsDbEntry 4 }

  rdbmsDbContact  OBJECT-TYPE
      SYNTAX      DisplayString
      MAX-ACCESS  read-write
      STATUS      current

      ::= { rdbmsDbEntry 5 }










  rdbmsDbInfoTable    OBJECT-TYPE
      SYNTAX          SEQUENCE OF RdbmsDbInfoEntry
      MAX-ACCESS      not-accessible
      STATUS          current
      ::= { rdbmsObjects 2 }

  rdbmsDbInfoEntry    OBJECT-TYPE
      SYNTAX          RdbmsDbInfoEntry
      MAX-ACCESS      not-accessible
      STATUS          current
      INDEX  { rdbmsDbIndex }
      ::= { rdbmsDbInfoTable 1 }

  RdbmsDbInfoEntry ::=
      SEQUENCE {
          rdbmsDbInfoProductName      DisplayString,
          rdbmsDbInfoVersion          DisplayString,
          rdbmsDbInfoSizeUnits        INTEGER,
          rdbmsDbInfoSizeAllocated    INTEGER,
          rdbmsDbInfoSizeUsed         INTEGER,
          rdbmsDbInfoLastBackup       DateAndTime
      }

  rdbmsDbInfoProductName  OBJECT-TYPE
      SYNTAX          DisplayString
      MAX-ACCESS      read-only
      STATUS          current
      ::= { rdbmsDbInfoEntry 1 }

  rdbmsDbInfoVersion  OBJECT-TYPE
      SYNTAX          DisplayString
      MAX-ACCESS      read-only





      STATUS          current
      ::= { rdbmsDbInfoEntry 2 }

  rdbmsDbInfoSizeUnits    OBJECT-TYPE
      SYNTAX              INTEGER {
                              bytes(1),
                              kbytes(2),
                              mbytes(3),
                              gbytes(4),
                              tbytes(5)
                              }
      MAX-ACCESS          read-only
      STATUS              current

      ::= { rdbmsDbInfoEntry 3 }

  rdbmsDbInfoSizeAllocated    OBJECT-TYPE
      SYNTAX                  INTEGER (1..2147483647)
      MAX-ACCESS              read-write
      STATUS                  current


      ::= { rdbmsDbInfoEntry 4 }





  rdbmsDbInfoSizeUsed     OBJECT-TYPE
      SYNTAX              INTEGER (1..2147483647)
      MAX-ACCESS          read-only
      STATUS              current

      ::= { rdbmsDbInfoEntry 5 }

  rdbmsDbInfoLastBackup       OBJECT-TYPE
       SYNTAX                 DateAndTime
       MAX-ACCESS             read-only
       STATUS                 current
       ::= { rdbmsDbInfoEntry 6 }


  rdbmsDbParamTable       OBJECT-TYPE
      SYNTAX              SEQUENCE OF RdbmsDbParamEntry
      MAX-ACCESS          not-accessible
      STATUS              current
      ::= { rdbmsObjects 3 }

  rdbmsDbParamEntry       OBJECT-TYPE
      SYNTAX              RdbmsDbParamEntry
      MAX-ACCESS          not-accessible
      STATUS              current
      INDEX  { rdbmsDbIndex, rdbmsDbParamName, rdbmsDbParamSubIndex }
      ::= { rdbmsDbParamTable 1 }

  RdbmsDbParamEntry ::=
      SEQUENCE {
          rdbmsDbParamName                DisplayString,
          rdbmsDbParamSubIndex            INTEGER,
          rdbmsDbParamID                  AutonomousType,
          rdbmsDbParamCurrValue           DisplayString,
          rdbmsDbParamComment             DisplayString
      }

  rdbmsDbParamName        OBJECT-TYPE
      SYNTAX              DisplayString (SIZE (1..64))
      MAX-ACCESS          not-accessible





      STATUS              current

      ::= { rdbmsDbParamEntry 1 }

  rdbmsDbParamSubIndex    OBJECT-TYPE
      SYNTAX              INTEGER (1..2147483647)
      MAX-ACCESS          not-accessible
      STATUS              current
      ::= { rdbmsDbParamEntry 2 }

  rdbmsDbParamID          OBJECT-TYPE
      SYNTAX              AutonomousType
      MAX-ACCESS          read-only
      STATUS              current
      ::= { rdbmsDbParamEntry 3 }

  rdbmsDbParamCurrValue OBJECT-TYPE
      SYNTAX              DisplayString
      MAX-ACCESS          read-write
      STATUS              current

      ::= { rdbmsDbParamEntry 4 }

  rdbmsDbParamComment     OBJECT-TYPE
      SYNTAX              DisplayString
      MAX-ACCESS          read-write
      STATUS              current

      ::= { rdbmsDbParamEntry 5 }


  rdbmsDbLimitedResourceTable         OBJECT-TYPE
      SYNTAX          SEQUENCE OF RdbmsDbLimitedResourceEntry
      MAX-ACCESS      not-accessible
      STATUS          current
      ::= { rdbmsObjects 4 }

  rdbmsDbLimitedResourceEntry     OBJECT-TYPE
      SYNTAX      RdbmsDbLimitedResourceEntry
      MAX-ACCESS  not-accessible
      STATUS      current

      INDEX { rdbmsDbIndex, rdbmsDbLimitedResourceName }
      ::= { rdbmsDbLimitedResourceTable 1 }

  RdbmsDbLimitedResourceEntry ::=
      SEQUENCE {
          rdbmsDbLimitedResourceName          DisplayString,
          rdbmsDbLimitedResourceID            AutonomousType,
          rdbmsDbLimitedResourceLimit         INTEGER,
          rdbmsDbLimitedResourceCurrent       INTEGER,
          rdbmsDbLimitedResourceHighwater     INTEGER,
          rdbmsDbLimitedResourceFailures      Counter32,
          rdbmsDbLimitedResourceDescription   DisplayString
      }

  rdbmsDbLimitedResourceName          OBJECT-TYPE
      SYNTAX          DisplayString
      MAX-ACCESS      not-accessible
      STATUS          current
      ::= { rdbmsDbLimitedResourceEntry  1 }

  rdbmsDbLimitedResourceID OBJECT-TYPE
      SYNTAX              AutonomousType
      MAX-ACCESS          read-only
      STATUS              current
      ::= { rdbmsDbLimitedResourceEntry 2 }

  rdbmsDbLimitedResourceLimit         OBJECT-TYPE
      SYNTAX          INTEGER (1..2147483647)
      MAX-ACCESS      read-write
      STATUS          current






      ::= { rdbmsDbLimitedResourceEntry  3 }

  rdbmsDbLimitedResourceCurrent       OBJECT-TYPE
      SYNTAX          INTEGER (1..2147483647)
      MAX-ACCESS      read-only
      STATUS          current
      ::= { rdbmsDbLimitedResourceEntry  4 }

  rdbmsDbLimitedResourceHighwater     OBJECT-TYPE
      SYNTAX          INTEGER (1..2147483647)
      MAX-ACCESS      read-only
      STATUS          current
      ::= { rdbmsDbLimitedResourceEntry  5 }

  rdbmsDbLimitedResourceFailures      OBJECT-TYPE
      SYNTAX          Counter32
      MAX-ACCESS      read-only
      STATUS          current
      ::= { rdbmsDbLimitedResourceEntry  6 }

  rdbmsDbLimitedResourceDescription           OBJECT-TYPE
      SYNTAX          DisplayString
      MAX-ACCESS      read-write
      STATUS          current






      ::= { rdbmsDbLimitedResourceEntry  7 }


  rdbmsSrvTable       OBJECT-TYPE
      SYNTAX          SEQUENCE OF RdbmsSrvEntry
      MAX-ACCESS      not-accessible
      STATUS          current
      ::= { rdbmsObjects 5 }

  rdbmsSrvEntry   OBJECT-TYPE
      SYNTAX      RdbmsSrvEntry
      MAX-ACCESS  not-accessible
      STATUS      current
      INDEX { applIndex }
      ::= { rdbmsSrvTable 1 }

  RdbmsSrvEntry ::=
      SEQUENCE {
          rdbmsSrvPrivateMibOID   OBJECT IDENTIFIER,
          rdbmsSrvVendorName  DisplayString,
          rdbmsSrvProductName DisplayString,
          rdbmsSrvContact     DisplayString
      }

  rdbmsSrvPrivateMibOID   OBJECT-TYPE
      SYNTAX          OBJECT IDENTIFIER
      MAX-ACCESS      read-only
      STATUS          current
      ::= { rdbmsSrvEntry  1 }

  rdbmsSrvVendorName  OBJECT-TYPE
      SYNTAX          DisplayString
      MAX-ACCESS      read-only
      STATUS          current
      ::= { rdbmsSrvEntry 2 }

  rdbmsSrvProductName  OBJECT-TYPE
      SYNTAX          DisplayString
      MAX-ACCESS      read-only
      STATUS          current
      ::= { rdbmsSrvEntry 3 }

  rdbmsSrvContact OBJECT-TYPE
      SYNTAX      DisplayString
      MAX-ACCESS  read-write
      STATUS      current

      ::= { rdbmsSrvEntry 4 }






  rdbmsSrvInfoTable   OBJECT-TYPE
      SYNTAX          SEQUENCE OF RdbmsSrvInfoEntry
      MAX-ACCESS      not-accessible
      STATUS          current

      ::= { rdbmsObjects 6 }

  rdbmsSrvInfoEntry   OBJECT-TYPE
      SYNTAX          RdbmsSrvInfoEntry
      MAX-ACCESS      not-accessible
      STATUS          current
      INDEX { applIndex }
      ::= { rdbmsSrvInfoTable 1 }

  RdbmsSrvInfoEntry ::=
      SEQUENCE {
          rdbmsSrvInfoStartupTime                 DateAndTime,
          rdbmsSrvInfoFinishedTransactions        Gauge32,
          rdbmsSrvInfoDiskReads                   Counter32,
          rdbmsSrvInfoDiskWrites                  Counter32,
          rdbmsSrvInfoLogicalReads                Counter32,
          rdbmsSrvInfoLogicalWrites               Counter32,
          rdbmsSrvInfoPageWrites                  Counter32,
          rdbmsSrvInfoPageReads                   Counter32,
          rdbmsSrvInfoDiskOutOfSpaces             Counter32,
          rdbmsSrvInfoHandledRequests             Counter32,
          rdbmsSrvInfoRequestRecvs                Counter32,
          rdbmsSrvInfoRequestSends                Counter32,
          rdbmsSrvInfoHighwaterInboundAssociations        Gauge32,
          rdbmsSrvInfoMaxInboundAssociations              Gauge32
      }

  rdbmsSrvInfoStartupTime  OBJECT-TYPE
      SYNTAX              DateAndTime
      MAX-ACCESS          read-only





      STATUS              current
      ::= { rdbmsSrvInfoEntry 1 }

  rdbmsSrvInfoFinishedTransactions  OBJECT-TYPE
      SYNTAX              Gauge32
      MAX-ACCESS          read-only
      STATUS              current
      ::= { rdbmsSrvInfoEntry 2 }

  rdbmsSrvInfoDiskReads   OBJECT-TYPE
      SYNTAX              Counter32
      MAX-ACCESS          read-only
      STATUS              current
      ::= { rdbmsSrvInfoEntry 3 }

  rdbmsSrvInfoLogicalReads    OBJECT-TYPE
      SYNTAX                  Counter32
      MAX-ACCESS              read-only
      STATUS                  current
      ::= { rdbmsSrvInfoEntry 4 }

  rdbmsSrvInfoDiskWrites  OBJECT-TYPE
      SYNTAX              Counter32
      MAX-ACCESS          read-only
      STATUS              current





      ::= { rdbmsSrvInfoEntry 5 }

  rdbmsSrvInfoLogicalWrites  OBJECT-TYPE
      SYNTAX              Counter32
      MAX-ACCESS          read-only
      STATUS              current
      ::= { rdbmsSrvInfoEntry 6 }

  rdbmsSrvInfoPageReads   OBJECT-TYPE
      SYNTAX              Counter32
      MAX-ACCESS          read-only
      STATUS              current
      ::= { rdbmsSrvInfoEntry 7}

  rdbmsSrvInfoPageWrites  OBJECT-TYPE
      SYNTAX              Counter32
      MAX-ACCESS          read-only
      STATUS              current
      ::= { rdbmsSrvInfoEntry 8 }

  rdbmsSrvInfoDiskOutOfSpaces OBJECT-TYPE
      SYNTAX                  Counter32
      MAX-ACCESS              read-only
      STATUS                  current
      ::= { rdbmsSrvInfoEntry 9 }

  rdbmsSrvInfoHandledRequests     OBJECT-TYPE
      SYNTAX              Counter32
      MAX-ACCESS          read-only
      STATUS              current
      ::= { rdbmsSrvInfoEntry 10 }

  rdbmsSrvInfoRequestRecvs        OBJECT-TYPE
      SYNTAX              Counter32
      MAX-ACCESS          read-only
      STATUS              current
      ::= { rdbmsSrvInfoEntry 11 }

  rdbmsSrvInfoRequestSends        OBJECT-TYPE
      SYNTAX              Counter32
      MAX-ACCESS          read-only
      STATUS              current
      ::= { rdbmsSrvInfoEntry 12 }

  rdbmsSrvInfoHighwaterInboundAssociations  OBJECT-TYPE
      SYNTAX              Gauge32
      MAX-ACCESS          read-only
      STATUS              current
      ::= { rdbmsSrvInfoEntry 13 }

  rdbmsSrvInfoMaxInboundAssociations OBJECT-TYPE
      SYNTAX              Gauge32
      MAX-ACCESS          read-write
      STATUS              current

      ::= { rdbmsSrvInfoEntry 14 }


  rdbmsSrvParamTable      OBJECT-TYPE
      SYNTAX              SEQUENCE OF RdbmsSrvParamEntry
      MAX-ACCESS          not-accessible
      STATUS              current
      ::= { rdbmsObjects 7 }

  rdbmsSrvParamEntry      OBJECT-TYPE
      SYNTAX              RdbmsSrvParamEntry
      MAX-ACCESS          not-accessible
      STATUS              current
      INDEX  { applIndex, rdbmsSrvParamName, rdbmsSrvParamSubIndex }
      ::= { rdbmsSrvParamTable 1 }

  RdbmsSrvParamEntry ::=
      SEQUENCE {
          rdbmsSrvParamName           DisplayString,
          rdbmsSrvParamSubIndex       INTEGER,
          rdbmsSrvParamID             AutonomousType,





          rdbmsSrvParamCurrValue      DisplayString,
          rdbmsSrvParamComment        DisplayString
      }

  rdbmsSrvParamName       OBJECT-TYPE
      SYNTAX              DisplayString (SIZE (1..64))
      MAX-ACCESS          not-accessible
      STATUS              current
      ::= { rdbmsSrvParamEntry 1 }

  rdbmsSrvParamSubIndex   OBJECT-TYPE
      SYNTAX              INTEGER (1..2147483647)
      MAX-ACCESS          not-accessible
      STATUS              current
      ::= { rdbmsSrvParamEntry 2 }

  rdbmsSrvParamID         OBJECT-TYPE
      SYNTAX              AutonomousType
      MAX-ACCESS          read-only
      STATUS              current
      ::= { rdbmsSrvParamEntry 3 }

  rdbmsSrvParamCurrValue  OBJECT-TYPE
      SYNTAX              DisplayString
      MAX-ACCESS          read-write





      STATUS              current

      ::= { rdbmsSrvParamEntry 4 }

  rdbmsSrvParamComment    OBJECT-TYPE
      SYNTAX              DisplayString
      MAX-ACCESS          read-write
      STATUS              current

      ::= { rdbmsSrvParamEntry 5 }


  rdbmsSrvLimitedResourceTable        OBJECT-TYPE
      SYNTAX          SEQUENCE OF RdbmsSrvLimitedResourceEntry
      MAX-ACCESS      not-accessible
      STATUS          current
      ::= { rdbmsObjects 8 }

  rdbmsSrvLimitedResourceEntry    OBJECT-TYPE
      SYNTAX      RdbmsSrvLimitedResourceEntry
      MAX-ACCESS  not-accessible
      STATUS      current
      INDEX { applIndex, rdbmsSrvLimitedResourceName }
      ::= { rdbmsSrvLimitedResourceTable 1 }

  RdbmsSrvLimitedResourceEntry ::=
      SEQUENCE {
          rdbmsSrvLimitedResourceName         DisplayString,
          rdbmsSrvLimitedResourceID           AutonomousType,
          rdbmsSrvLimitedResourceLimit        INTEGER,
          rdbmsSrvLimitedResourceCurrent      INTEGER,
          rdbmsSrvLimitedResourceHighwater    INTEGER,
          rdbmsSrvLimitedResourceFailures     Counter32,
          rdbmsSrvLimitedResourceDescription  DisplayString
      }

  rdbmsSrvLimitedResourceName         OBJECT-TYPE
      SYNTAX          DisplayString
      MAX-ACCESS      not-accessible
      STATUS          current
      ::= { rdbmsSrvLimitedResourceEntry  1 }

  rdbmsSrvLimitedResourceID OBJECT-TYPE
      SYNTAX              AutonomousType
      MAX-ACCESS          read-only
      STATUS              current
      ::= { rdbmsSrvLimitedResourceEntry 2 }

  rdbmsSrvLimitedResourceLimit        OBJECT-TYPE
      SYNTAX          INTEGER (1..2147483647)
      MAX-ACCESS      read-write
      STATUS          current










      ::= { rdbmsSrvLimitedResourceEntry  3 }

  rdbmsSrvLimitedResourceCurrent      OBJECT-TYPE
      SYNTAX          INTEGER (1..2147483647)
      MAX-ACCESS      read-only
      STATUS          current
      ::= { rdbmsSrvLimitedResourceEntry  4 }

  rdbmsSrvLimitedResourceHighwater            OBJECT-TYPE
      SYNTAX          INTEGER (1..2147483647)
      MAX-ACCESS      read-only
      STATUS          current
      ::= { rdbmsSrvLimitedResourceEntry  5 }

  rdbmsSrvLimitedResourceFailures     OBJECT-TYPE
      SYNTAX          Counter32
      MAX-ACCESS      read-only
      STATUS          current
      ::= { rdbmsSrvLimitedResourceEntry  6 }

  rdbmsSrvLimitedResourceDescription    OBJECT-TYPE
      SYNTAX          DisplayString
      MAX-ACCESS      read-write
      STATUS          current

      ::= { rdbmsSrvLimitedResourceEntry  7 }








  rdbmsRelTable   OBJECT-TYPE
      SYNTAX      SEQUENCE OF RdbmsRelEntry
      MAX-ACCESS  not-accessible
      STATUS      current
      ::= { rdbmsObjects 9 }

  rdbmsRelEntry   OBJECT-TYPE
      SYNTAX      RdbmsRelEntry
      MAX-ACCESS  not-accessible
      STATUS      current
      INDEX  { rdbmsDbIndex, applIndex }
      ::= { rdbmsRelTable 1 }

  RdbmsRelEntry ::=
      SEQUENCE {
           rdbmsRelState          INTEGER,
           rdbmsRelActiveTime     DateAndTime
      }

  rdbmsRelState   OBJECT-TYPE
      SYNTAX      INTEGER{
                      other(1),
                      active(2),
                      available(3),
                      restricted(4),
                      unavailable(5)
                      }
      MAX-ACCESS  read-only
      STATUS      current

      ::= { rdbmsRelEntry 1 }

  rdbmsRelActiveTime  OBJECT-TYPE
      SYNTAX          DateAndTime
      MAX-ACCESS      read-only
      STATUS          current
      ::= { rdbmsRelEntry 2 }



  rdbmsWellKnownLimitedResources OBJECT IDENTIFIER
          ::= { rdbmsObjects 10 }

  rdbmsLogSpace   OBJECT-IDENTITY
                  STATUS  current
          ::= { rdbmsWellKnownLimitedResources 1}


  rdbmsTraps       OBJECT IDENTIFIER ::= { rdbmsMIB 2 }

  rdbmsStateChange    NOTIFICATION-TYPE
      OBJECTS         { rdbmsRelState }
      STATUS          current
      ::= { rdbmsTraps 1 }

  rdbmsOutOfSpace NOTIFICATION-TYPE
      OBJECTS     { rdbmsSrvInfoDiskOutOfSpaces }
      STATUS      current
      ::= { rdbmsTraps 2 }



  rdbmsConformance    OBJECT IDENTIFIER ::= { rdbmsMIB 3 }
  rdbmsCompliances    OBJECT IDENTIFIER ::= { rdbmsConformance 1 }
  rdbmsGroups         OBJECT IDENTIFIER ::= { rdbmsConformance 2 }


  rdbmsCompliance     MODULE-COMPLIANCE
      STATUS          current
      MODULE HOST-RESOURCES-MIB
          MANDATORY-GROUPS    { hrSystem }
      MODULE APPLICATION-MIB
          MANDATORY-GROUPS { applGroups }
      MODULE RDBMS-MIB
          MANDATORY-GROUPS { rdbmsGroup }

      GROUP  rdbmsGroup
          OBJECT      rdbmsDbContact
          MIN-ACCESS  read-only
          OBJECT      rdbmsDbParamCurrValue
          MIN-ACCESS  read-only
          OBJECT      rdbmsDbParamComment
          MIN-ACCESS  read-only
          OBJECT      rdbmsDbLimitedResourceLimit
          MIN-ACCESS  read-only
          OBJECT      rdbmsDbLimitedResourceDescription
          MIN-ACCESS  read-only
          OBJECT      rdbmsSrvContact
          MIN-ACCESS  read-only
          OBJECT      rdbmsSrvInfoMaxInboundAssociations
          MIN-ACCESS  read-only
          OBJECT      rdbmsSrvParamCurrValue
          MIN-ACCESS  read-only
          OBJECT      rdbmsSrvParamComment
          MIN-ACCESS  read-only
          OBJECT      rdbmsSrvLimitedResourceLimit
          MIN-ACCESS  read-only
          OBJECT      rdbmsSrvLimitedResourceDescription





          MIN-ACCESS  read-only

      ::= { rdbmsCompliances 1 }



  rdbmsGroup   OBJECT-GROUP
      OBJECTS  {
                  rdbmsDbPrivateMibOID, rdbmsDbVendorName,
                  rdbmsDbName, rdbmsDbContact,

                  rdbmsDbInfoProductName, rdbmsDbInfoVersion,
                  rdbmsDbInfoSizeUnits, rdbmsDbInfoSizeAllocated,
                  rdbmsDbInfoSizeUsed, rdbmsDbInfoLastBackup,

                  rdbmsDbParamCurrValue, rdbmsDbParamComment,

                  rdbmsDbLimitedResourceLimit,
                  rdbmsDbLimitedResourceCurrent,
                  rdbmsDbLimitedResourceHighwater,
                  rdbmsDbLimitedResourceFailures,
                  rdbmsDbLimitedResourceDescription,

                  rdbmsSrvPrivateMibOID, rdbmsSrvVendorName,
                  rdbmsSrvProductName, rdbmsSrvContact,

                  rdbmsSrvInfoStartupTime,
                  rdbmsSrvInfoFinishedTransactions,
                  rdbmsSrvInfoDiskReads, rdbmsSrvInfoDiskWrites,
                  rdbmsSrvInfoLogicalReads, rdbmsSrvInfoLogicalWrites,
                  rdbmsSrvInfoPageReads, rdbmsSrvInfoPageWrites,
                  rdbmsSrvInfoHandledRequests,
                  rdbmsSrvInfoRequestRecvs, rdbmsSrvInfoRequestSends,
                  rdbmsSrvInfoHighwaterInboundAssociations,
                  rdbmsSrvInfoMaxInboundAssociations,

                  rdbmsSrvParamCurrValue, rdbmsSrvParamComment,

                  rdbmsSrvLimitedResourceLimit,
                  rdbmsSrvLimitedResourceCurrent,
                  rdbmsSrvLimitedResourceHighwater,





                  rdbmsSrvLimitedResourceFailures,
                  rdbmsSrvLimitedResourceDescription,

                  rdbmsRelState, rdbmsRelActiveTime }
      STATUS   current
      ::= { rdbmsGroups 1 }


  END
