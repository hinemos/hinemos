PerfHist-TC-MIB DEFINITIONS ::= BEGIN

   IMPORTS
      MODULE-IDENTITY,
      Gauge32, mib-2
          FROM SNMPv2-SMI
      TEXTUAL-CONVENTION
          FROM SNMPv2-TC;

   perfHistTCMIB MODULE-IDENTITY
        LAST-UPDATED "200308130000Z"
        ORGANIZATION "IETF AToM MIB WG"

        ::= { mib-2 58 }














   PerfCurrentCount ::= TEXTUAL-CONVENTION
         STATUS  current
          SYNTAX  Gauge32











   PerfIntervalCount ::= TEXTUAL-CONVENTION
         STATUS  current
          SYNTAX  Gauge32

   PerfTotalCount ::= TEXTUAL-CONVENTION
         STATUS  current
          SYNTAX  Gauge32

   END
