DS1-MIB DEFINITIONS ::= BEGIN

   IMPORTS
        MODULE-IDENTITY, OBJECT-TYPE,
        NOTIFICATION-TYPE, transmission
        FROM SNMPv2-SMI         -- [RFC2578]
        DisplayString, TimeStamp, TruthValue
        FROM SNMPv2-TC          -- [RFC2579]
        MODULE-COMPLIANCE, OBJECT-GROUP,
        NOTIFICATION-GROUP
        FROM SNMPv2-CONF        -- [RFC2580]
        InterfaceIndex, ifIndex
        FROM IF-MIB             -- [RFC2863]
        PerfCurrentCount, PerfIntervalCount,
        PerfTotalCount
        FROM PerfHist-TC-MIB;   -- [RFC3593]

   ds1 MODULE-IDENTITY
       LAST-UPDATED "200703050000Z"
       ORGANIZATION "IETF AToM MIB Working Group"








       ::= { transmission 18 }




   dsx1ConfigTable OBJECT-TYPE
        SYNTAX  SEQUENCE OF Dsx1ConfigEntry
        MAX-ACCESS  not-accessible
        STATUS  current
        ::= { ds1 6 }

   dsx1ConfigEntry OBJECT-TYPE
        SYNTAX  Dsx1ConfigEntry
        MAX-ACCESS  not-accessible
        STATUS  current
        INDEX   { dsx1LineIndex }
        ::= { dsx1ConfigTable 1 }

   Dsx1ConfigEntry ::=
        SEQUENCE {
              dsx1LineIndex                    InterfaceIndex,
              dsx1IfIndex                      InterfaceIndex,
              dsx1TimeElapsed                  INTEGER,
              dsx1ValidIntervals               INTEGER,
              dsx1LineType                     INTEGER,
              dsx1LineCoding                   INTEGER,
              dsx1SendCode                     INTEGER,





              dsx1CircuitIdentifier            DisplayString,
              dsx1LoopbackConfig               INTEGER,
              dsx1LineStatus                   INTEGER,
              dsx1SignalMode                   INTEGER,
              dsx1TransmitClockSource          INTEGER,
              dsx1Fdl                          INTEGER,
              dsx1InvalidIntervals             INTEGER,
              dsx1LineLength                   INTEGER,
              dsx1LineStatusLastChange         TimeStamp,
              dsx1LineStatusChangeTrapEnable   INTEGER,
              dsx1LoopbackStatus               INTEGER,
              dsx1Ds1ChannelNumber             INTEGER,
              dsx1Channelization               INTEGER,
              dsx1LineMode                     INTEGER,
              dsx1LineBuildOut                 INTEGER,
              dsx1LineImpedance                INTEGER
   }

   dsx1LineIndex OBJECT-TYPE
        SYNTAX  InterfaceIndex
        MAX-ACCESS  read-only  -- read-only since originally an
        STATUS  current
        ::= { dsx1ConfigEntry 1 }

   dsx1IfIndex OBJECT-TYPE
        SYNTAX  InterfaceIndex
        MAX-ACCESS  read-only
        STATUS  deprecated
        ::= { dsx1ConfigEntry 2 }

   dsx1TimeElapsed OBJECT-TYPE
        SYNTAX  INTEGER (0..899)
        MAX-ACCESS  read-only
        STATUS  current
        ::= { dsx1ConfigEntry 3 }

   dsx1ValidIntervals OBJECT-TYPE
        SYNTAX  INTEGER (0..96)
        MAX-ACCESS  read-only
        STATUS  current
        ::= { dsx1ConfigEntry 4 }

   dsx1LineType OBJECT-TYPE
        SYNTAX INTEGER {
                  other(1),
                  dsx1ESF(2),
                  dsx1D4(3),
                  dsx1E1(4),
                  dsx1E1CRC(5),
                  dsx1E1MF(6),
                  dsx1E1CRCMF(7),
                  dsx1Unframed(8),
                  dsx1E1Unframed(9),
                  dsx1DS2M12(10),
                  dsx1E2(11),
                  dsx1E1Q50(12),
                  dsx1E1Q50CRC(13),





                  dsx1J1ESF(14),
                  dsx1J1Unframed(16)
                                  }
        MAX-ACCESS read-write
        STATUS current
   ::= { dsx1ConfigEntry 5 }

   dsx1LineCoding OBJECT-TYPE
        SYNTAX  INTEGER {
                   dsx1JBZS(1),
                   dsx1B8ZS(2),
                   dsx1HDB3(3),
                   dsx1ZBTSI(4),
                   dsx1AMI(5),
                   other(6),
                   dsx1B6ZS(7)
               }
        MAX-ACCESS  read-write
        STATUS  current
        ::= { dsx1ConfigEntry 6 }

   dsx1SendCode OBJECT-TYPE
        SYNTAX  INTEGER {
                  dsx1SendNoCode(1),
                  dsx1SendLineCode(2),
                  dsx1SendPayloadCode(3),
                  dsx1SendResetCode(4),
                  dsx1SendQRS(5),
                  dsx1Send511Pattern(6),
                  dsx1Send3in24Pattern(7),
                  dsx1SendOtherTestPattern(8)
                  }
        MAX-ACCESS  read-write
        STATUS  current
        ::= { dsx1ConfigEntry 7 }

   dsx1CircuitIdentifier OBJECT-TYPE
        SYNTAX  DisplayString (SIZE (0..255))
        MAX-ACCESS  read-write
        STATUS  current
        ::= { dsx1ConfigEntry 8 }

   dsx1LoopbackConfig OBJECT-TYPE
        SYNTAX  INTEGER {
                    dsx1NoLoop(1),
                    dsx1PayloadLoop(2),
                    dsx1LineLoop(3),
                    dsx1OtherLoop(4),
                    dsx1InwardLoop(5),
                    dsx1DualLoop(6)
                  }
        MAX-ACCESS  read-write
        STATUS  current
        ::= { dsx1ConfigEntry 9 }

   dsx1LineStatus OBJECT-TYPE
        SYNTAX  INTEGER (1..131071)
        MAX-ACCESS  read-only
        STATUS  current
        ::= { dsx1ConfigEntry 10 }

   dsx1SignalMode OBJECT-TYPE
        SYNTAX  INTEGER {
                   none(1),
                   robbedBit(2),
                   bitOriented(3),
                   messageOriented(4),
                   other(5)
               }
        MAX-ACCESS  read-write
        STATUS  current
        ::= { dsx1ConfigEntry 11 }





   dsx1TransmitClockSource OBJECT-TYPE
        SYNTAX  INTEGER {
                   loopTiming(1),
                   localTiming(2),
                   throughTiming(3),
                   adaptive (4)
               }
        MAX-ACCESS  read-write
        STATUS  current
        ::= { dsx1ConfigEntry 12 }

   dsx1Fdl OBJECT-TYPE
        SYNTAX  INTEGER (1..15)
        MAX-ACCESS  read-write
        STATUS  current
        ::= { dsx1ConfigEntry 13 }

   dsx1InvalidIntervals OBJECT-TYPE
        SYNTAX  INTEGER (0..96)
        MAX-ACCESS  read-only
        STATUS  current
        ::= { dsx1ConfigEntry 14 }

   dsx1LineLength OBJECT-TYPE
        SYNTAX  INTEGER (0..64000)
        UNITS  "meters"
        MAX-ACCESS  read-write
        STATUS  current
        ::= { dsx1ConfigEntry 15 }

   dsx1LineStatusLastChange OBJECT-TYPE
        SYNTAX  TimeStamp
        MAX-ACCESS  read-only
        STATUS  current
        ::= { dsx1ConfigEntry 16 }

   dsx1LineStatusChangeTrapEnable  OBJECT-TYPE
        SYNTAX      INTEGER {
                       enabled(1),
                       disabled(2)
                    }





        MAX-ACCESS  read-write
        STATUS      current
        DEFVAL { disabled }
        ::= { dsx1ConfigEntry 17 }

   dsx1LoopbackStatus  OBJECT-TYPE
        SYNTAX      INTEGER (1..127)
        MAX-ACCESS  read-only
        STATUS      current

        ::= { dsx1ConfigEntry 18 }

   dsx1Ds1ChannelNumber  OBJECT-TYPE
        SYNTAX      INTEGER (0..28)
        MAX-ACCESS  read-only
        STATUS      current
        ::= { dsx1ConfigEntry 19 }

   dsx1Channelization  OBJECT-TYPE
        SYNTAX      INTEGER {
                       disabled(1),
                       enabledDs0(2),





                       enabledDs1(3)
                    }
        MAX-ACCESS  read-write
        STATUS      current

        ::= { dsx1ConfigEntry 20 }

   dsx1LineMode  OBJECT-TYPE
        SYNTAX      INTEGER {
                       csu(1),
                       dsu(2)
                     }
        MAX-ACCESS  read-write
        STATUS      current
        ::= { dsx1ConfigEntry 21 }

   dsx1LineBuildOut  OBJECT-TYPE
        SYNTAX      INTEGER {
                       notApplicable(1),
                       neg75dB(2),
                       neg15dB(3),
                       neg225dB(4),
                       zerodB(5)
                    }
        MAX-ACCESS  read-write
        STATUS      current





        ::= { dsx1ConfigEntry 22 }

   dsx1LineImpedance   OBJECT-TYPE
        SYNTAX      INTEGER {
                       notApplicable(1),
                       unbalanced75ohms(2),
                       balanced100ohms(3),
                       balanced120ohms(4)
                    }
        MAX-ACCESS  read-write
        STATUS      current
        ::= { dsx1ConfigEntry 23 }

   dsx1CurrentTable OBJECT-TYPE
        SYNTAX  SEQUENCE OF Dsx1CurrentEntry
        MAX-ACCESS  not-accessible
        STATUS  current
        ::= { ds1 7 }

   dsx1CurrentEntry OBJECT-TYPE
        SYNTAX  Dsx1CurrentEntry
        MAX-ACCESS  not-accessible
        STATUS  current
        INDEX   { dsx1CurrentIndex }
        ::= { dsx1CurrentTable 1 }

   Dsx1CurrentEntry ::=
        SEQUENCE {
            dsx1CurrentIndex            InterfaceIndex,
            dsx1CurrentESs              PerfCurrentCount,
            dsx1CurrentSESs             PerfCurrentCount,
            dsx1CurrentSEFSs            PerfCurrentCount,
            dsx1CurrentUASs             PerfCurrentCount,
            dsx1CurrentCSSs             PerfCurrentCount,





            dsx1CurrentPCVs             PerfCurrentCount,
            dsx1CurrentLESs             PerfCurrentCount,
            dsx1CurrentBESs             PerfCurrentCount,
            dsx1CurrentDMs              PerfCurrentCount,
            dsx1CurrentLCVs             PerfCurrentCount
   }

   dsx1CurrentIndex OBJECT-TYPE
        SYNTAX  InterfaceIndex
        MAX-ACCESS  read-only  -- read-only since originally an
        STATUS  current
        ::= { dsx1CurrentEntry 1 }

   dsx1CurrentESs OBJECT-TYPE
        SYNTAX  PerfCurrentCount
        MAX-ACCESS  read-only
        STATUS  current
        ::= { dsx1CurrentEntry 2 }

   dsx1CurrentSESs OBJECT-TYPE
        SYNTAX  PerfCurrentCount
        MAX-ACCESS  read-only
        STATUS  current
        ::= { dsx1CurrentEntry 3 }

   dsx1CurrentSEFSs OBJECT-TYPE
        SYNTAX  PerfCurrentCount
        MAX-ACCESS  read-only
        STATUS  current
        ::= { dsx1CurrentEntry 4 }

   dsx1CurrentUASs OBJECT-TYPE
        SYNTAX  PerfCurrentCount
        MAX-ACCESS  read-only
        STATUS  current





        ::= { dsx1CurrentEntry 5 }

   dsx1CurrentCSSs OBJECT-TYPE
        SYNTAX  PerfCurrentCount
        MAX-ACCESS  read-only
        STATUS  current
        ::= { dsx1CurrentEntry 6 }

   dsx1CurrentPCVs OBJECT-TYPE
        SYNTAX  PerfCurrentCount
        MAX-ACCESS  read-only
        STATUS  current
        ::= { dsx1CurrentEntry 7 }

   dsx1CurrentLESs OBJECT-TYPE
        SYNTAX  PerfCurrentCount
        MAX-ACCESS  read-only
        STATUS  current
        ::= { dsx1CurrentEntry 8 }

   dsx1CurrentBESs OBJECT-TYPE
        SYNTAX PerfCurrentCount
        MAX-ACCESS read-only
        STATUS current
        ::= { dsx1CurrentEntry 9 }

   dsx1CurrentDMs OBJECT-TYPE
        SYNTAX PerfCurrentCount
        MAX-ACCESS read-only
        STATUS deprecated
        ::= { dsx1CurrentEntry 10 }

   dsx1CurrentLCVs OBJECT-TYPE
        SYNTAX PerfCurrentCount
        MAX-ACCESS read-only
        STATUS current





        ::= { dsx1CurrentEntry 11 }

   dsx1IntervalTable OBJECT-TYPE
        SYNTAX  SEQUENCE OF Dsx1IntervalEntry
        MAX-ACCESS  not-accessible
        STATUS  current
        ::= { ds1 8 }

   dsx1IntervalEntry OBJECT-TYPE
        SYNTAX  Dsx1IntervalEntry
        MAX-ACCESS  not-accessible
        STATUS  current
        INDEX   { dsx1IntervalIndex, dsx1IntervalNumber }
        ::= { dsx1IntervalTable 1 }

   Dsx1IntervalEntry ::=
        SEQUENCE {
            dsx1IntervalIndex             InterfaceIndex,
            dsx1IntervalNumber            INTEGER,
            dsx1IntervalESs               PerfIntervalCount,
            dsx1IntervalSESs              PerfIntervalCount,
            dsx1IntervalSEFSs             PerfIntervalCount,
            dsx1IntervalUASs              PerfIntervalCount,
            dsx1IntervalCSSs              PerfIntervalCount,
            dsx1IntervalPCVs              PerfIntervalCount,
            dsx1IntervalLESs              PerfIntervalCount,
            dsx1IntervalBESs              PerfIntervalCount,
            dsx1IntervalDMs               PerfIntervalCount,
            dsx1IntervalLCVs              PerfIntervalCount,
            dsx1IntervalValidData         TruthValue
   }

   dsx1IntervalIndex OBJECT-TYPE
        SYNTAX  InterfaceIndex





        MAX-ACCESS  read-only  -- read-only since originally an
        STATUS  current
        ::= { dsx1IntervalEntry 1 }

   dsx1IntervalNumber OBJECT-TYPE
        SYNTAX  INTEGER (1..96)
        MAX-ACCESS  read-only  -- read-only since originally an
        STATUS  current
        ::= { dsx1IntervalEntry 2 }

   dsx1IntervalESs OBJECT-TYPE
        SYNTAX  PerfIntervalCount
        MAX-ACCESS  read-only
        STATUS  current
        ::= { dsx1IntervalEntry 3 }

   dsx1IntervalSESs OBJECT-TYPE
        SYNTAX  PerfIntervalCount
        MAX-ACCESS  read-only
        STATUS  current
        ::= { dsx1IntervalEntry 4 }

   dsx1IntervalSEFSs OBJECT-TYPE
        SYNTAX  PerfIntervalCount
        MAX-ACCESS  read-only
        STATUS  current
        ::= { dsx1IntervalEntry 5 }

   dsx1IntervalUASs OBJECT-TYPE





        SYNTAX  PerfIntervalCount
        MAX-ACCESS  read-only
        STATUS  current
        ::= { dsx1IntervalEntry 6 }

   dsx1IntervalCSSs OBJECT-TYPE
        SYNTAX  PerfIntervalCount
        MAX-ACCESS  read-only
        STATUS  current
        ::= { dsx1IntervalEntry 7 }

   dsx1IntervalPCVs OBJECT-TYPE
        SYNTAX  PerfIntervalCount
        MAX-ACCESS  read-only
        STATUS  current
        ::= { dsx1IntervalEntry 8 }

   dsx1IntervalLESs OBJECT-TYPE
        SYNTAX  PerfIntervalCount
        MAX-ACCESS  read-only
        STATUS  current
        ::= { dsx1IntervalEntry 9 }

   dsx1IntervalBESs OBJECT-TYPE
        SYNTAX PerfIntervalCount
        MAX-ACCESS read-only
        STATUS current
        ::= { dsx1IntervalEntry 10 }

   dsx1IntervalDMs OBJECT-TYPE
        SYNTAX PerfIntervalCount
        MAX-ACCESS read-only
        STATUS deprecated
        ::= { dsx1IntervalEntry 11 }





   dsx1IntervalLCVs OBJECT-TYPE
        SYNTAX PerfIntervalCount
        MAX-ACCESS read-only
        STATUS current
        ::= { dsx1IntervalEntry 12 }

   dsx1IntervalValidData OBJECT-TYPE
        SYNTAX TruthValue
        MAX-ACCESS read-only
        STATUS current
        ::= { dsx1IntervalEntry 13 }

   dsx1TotalTable OBJECT-TYPE
        SYNTAX  SEQUENCE OF Dsx1TotalEntry
        MAX-ACCESS  not-accessible
        STATUS  current
        ::= { ds1 9 }

   dsx1TotalEntry OBJECT-TYPE
        SYNTAX  Dsx1TotalEntry
        MAX-ACCESS  not-accessible
        STATUS  current
        INDEX   { dsx1TotalIndex }
        ::= { dsx1TotalTable 1 }

   Dsx1TotalEntry ::=
        SEQUENCE {
            dsx1TotalIndex                InterfaceIndex,
            dsx1TotalESs                  PerfTotalCount,
            dsx1TotalSESs                 PerfTotalCount,
            dsx1TotalSEFSs                PerfTotalCount,
            dsx1TotalUASs                 PerfTotalCount,
            dsx1TotalCSSs                 PerfTotalCount,
            dsx1TotalPCVs                 PerfTotalCount,
            dsx1TotalLESs                 PerfTotalCount,
            dsx1TotalBESs                 PerfTotalCount,





            dsx1TotalDMs                  PerfTotalCount,
            dsx1TotalLCVs                 PerfTotalCount
   }

   dsx1TotalIndex OBJECT-TYPE
        SYNTAX  InterfaceIndex
        MAX-ACCESS  read-only  -- read-only since originally an
        STATUS  current
        ::= { dsx1TotalEntry 1 }

   dsx1TotalESs OBJECT-TYPE
        SYNTAX  PerfTotalCount
        MAX-ACCESS  read-only
        STATUS  current
        ::= { dsx1TotalEntry 2 }

   dsx1TotalSESs OBJECT-TYPE
        SYNTAX  PerfTotalCount
        MAX-ACCESS  read-only
        STATUS  current
        ::= { dsx1TotalEntry 3 }

   dsx1TotalSEFSs OBJECT-TYPE
        SYNTAX  PerfTotalCount
        MAX-ACCESS  read-only
        STATUS  current
        ::= { dsx1TotalEntry 4 }





   dsx1TotalUASs OBJECT-TYPE
        SYNTAX  PerfTotalCount
        MAX-ACCESS  read-only
        STATUS  current
        ::= { dsx1TotalEntry 5 }

   dsx1TotalCSSs OBJECT-TYPE
        SYNTAX  PerfTotalCount
        MAX-ACCESS  read-only
        STATUS  current
        ::= { dsx1TotalEntry 6 }

   dsx1TotalPCVs OBJECT-TYPE
        SYNTAX  PerfTotalCount
        MAX-ACCESS  read-only
        STATUS  current
        ::= { dsx1TotalEntry 7 }

   dsx1TotalLESs OBJECT-TYPE
        SYNTAX  PerfTotalCount
        MAX-ACCESS  read-only
        STATUS  current
        ::= { dsx1TotalEntry 8 }

   dsx1TotalBESs OBJECT-TYPE
        SYNTAX PerfTotalCount
        MAX-ACCESS read-only
        STATUS current
        ::= { dsx1TotalEntry 9 }

   dsx1TotalDMs OBJECT-TYPE
        SYNTAX PerfTotalCount
        MAX-ACCESS read-only
        STATUS deprecated
        ::= { dsx1TotalEntry 10 }

   dsx1TotalLCVs OBJECT-TYPE
        SYNTAX PerfTotalCount
        MAX-ACCESS read-only
        STATUS current
        ::= { dsx1TotalEntry 11 }


   dsx1ChanMappingTable OBJECT-TYPE
        SYNTAX  SEQUENCE OF Dsx1ChanMappingEntry
        MAX-ACCESS  not-accessible
        STATUS  current
        ::= { ds1 16 }

   dsx1ChanMappingEntry OBJECT-TYPE
        SYNTAX  Dsx1ChanMappingEntry
        MAX-ACCESS  not-accessible
        STATUS  current
        INDEX   { ifIndex, dsx1Ds1ChannelNumber }
        ::= { dsx1ChanMappingTable 1 }

   Dsx1ChanMappingEntry ::=
        SEQUENCE {
            dsx1ChanMappedIfIndex  InterfaceIndex
   }

   dsx1ChanMappedIfIndex OBJECT-TYPE
        SYNTAX  InterfaceIndex
        MAX-ACCESS  read-only
        STATUS  current
        ::= { dsx1ChanMappingEntry 1 }


   dsx1FarEndCurrentTable OBJECT-TYPE
        SYNTAX  SEQUENCE OF Dsx1FarEndCurrentEntry
        MAX-ACCESS  not-accessible
        STATUS  current
        ::= { ds1 10 }

   dsx1FarEndCurrentEntry OBJECT-TYPE
        SYNTAX  Dsx1FarEndCurrentEntry
        MAX-ACCESS  not-accessible
        STATUS  current
        INDEX   { dsx1FarEndCurrentIndex }
        ::= { dsx1FarEndCurrentTable 1 }

   Dsx1FarEndCurrentEntry ::=
        SEQUENCE {
            dsx1FarEndCurrentIndex      InterfaceIndex,
            dsx1FarEndTimeElapsed       INTEGER,
            dsx1FarEndValidIntervals    INTEGER,
            dsx1FarEndCurrentESs        PerfCurrentCount,
            dsx1FarEndCurrentSESs       PerfCurrentCount,
            dsx1FarEndCurrentSEFSs      PerfCurrentCount,
            dsx1FarEndCurrentUASs       PerfCurrentCount,
            dsx1FarEndCurrentCSSs       PerfCurrentCount,
            dsx1FarEndCurrentLESs       PerfCurrentCount,
            dsx1FarEndCurrentPCVs       PerfCurrentCount,
            dsx1FarEndCurrentBESs       PerfCurrentCount,
            dsx1FarEndCurrentDMs        PerfCurrentCount,
            dsx1FarEndInvalidIntervals  INTEGER
   }

   dsx1FarEndCurrentIndex OBJECT-TYPE
        SYNTAX  InterfaceIndex
        MAX-ACCESS  read-only  -- read-only since originally an
        STATUS  current
        ::= { dsx1FarEndCurrentEntry 1 }

   dsx1FarEndTimeElapsed OBJECT-TYPE
        SYNTAX  INTEGER (0..899)
        MAX-ACCESS  read-only
        STATUS  current





        ::= { dsx1FarEndCurrentEntry 2 }

   dsx1FarEndValidIntervals OBJECT-TYPE
        SYNTAX  INTEGER (0..96)
        MAX-ACCESS  read-only
        STATUS  current
        ::= { dsx1FarEndCurrentEntry 3 }

   dsx1FarEndCurrentESs OBJECT-TYPE
        SYNTAX  PerfCurrentCount
        MAX-ACCESS  read-only
        STATUS  current
        ::= { dsx1FarEndCurrentEntry 4 }

   dsx1FarEndCurrentSESs OBJECT-TYPE
        SYNTAX  PerfCurrentCount
        MAX-ACCESS  read-only
        STATUS  current
        ::= { dsx1FarEndCurrentEntry 5 }

   dsx1FarEndCurrentSEFSs OBJECT-TYPE
        SYNTAX  PerfCurrentCount
        MAX-ACCESS  read-only
        STATUS  current
        ::= { dsx1FarEndCurrentEntry 6 }

   dsx1FarEndCurrentUASs OBJECT-TYPE
        SYNTAX  PerfCurrentCount
        MAX-ACCESS  read-only
        STATUS  current
        ::= { dsx1FarEndCurrentEntry 7 }

   dsx1FarEndCurrentCSSs OBJECT-TYPE
        SYNTAX  PerfCurrentCount
        MAX-ACCESS  read-only
        STATUS  current
        ::= { dsx1FarEndCurrentEntry 8 }

   dsx1FarEndCurrentLESs OBJECT-TYPE
        SYNTAX  PerfCurrentCount
        MAX-ACCESS  read-only
        STATUS  current
        ::= { dsx1FarEndCurrentEntry 9 }

   dsx1FarEndCurrentPCVs OBJECT-TYPE
        SYNTAX  PerfCurrentCount
        MAX-ACCESS  read-only
        STATUS  current
        ::= { dsx1FarEndCurrentEntry 10 }

   dsx1FarEndCurrentBESs OBJECT-TYPE
        SYNTAX PerfCurrentCount
        MAX-ACCESS read-only
        STATUS current
        ::= { dsx1FarEndCurrentEntry 11 }

   dsx1FarEndCurrentDMs OBJECT-TYPE
        SYNTAX PerfCurrentCount
        MAX-ACCESS read-only
        STATUS deprecated
        ::= { dsx1FarEndCurrentEntry 12 }

   dsx1FarEndInvalidIntervals OBJECT-TYPE
        SYNTAX  INTEGER (0..96)
        MAX-ACCESS  read-only
        STATUS  current
        ::= { dsx1FarEndCurrentEntry 13 }


   dsx1FarEndIntervalTable OBJECT-TYPE
        SYNTAX  SEQUENCE OF Dsx1FarEndIntervalEntry
        MAX-ACCESS  not-accessible
        STATUS  current
        ::= { ds1 11 }

   dsx1FarEndIntervalEntry OBJECT-TYPE
        SYNTAX  Dsx1FarEndIntervalEntry
        MAX-ACCESS  not-accessible
        STATUS  current
        INDEX   { dsx1FarEndIntervalIndex,
                  dsx1FarEndIntervalNumber }
        ::= { dsx1FarEndIntervalTable 1 }

   Dsx1FarEndIntervalEntry ::=
        SEQUENCE {
            dsx1FarEndIntervalIndex       InterfaceIndex,
            dsx1FarEndIntervalNumber      INTEGER,
            dsx1FarEndIntervalESs         PerfIntervalCount,
            dsx1FarEndIntervalSESs        PerfIntervalCount,





            dsx1FarEndIntervalSEFSs       PerfIntervalCount,
            dsx1FarEndIntervalUASs        PerfIntervalCount,
            dsx1FarEndIntervalCSSs        PerfIntervalCount,
            dsx1FarEndIntervalLESs        PerfIntervalCount,
            dsx1FarEndIntervalPCVs        PerfIntervalCount,
            dsx1FarEndIntervalBESs        PerfIntervalCount,
            dsx1FarEndIntervalDMs         PerfIntervalCount,
            dsx1FarEndIntervalValidData   TruthValue
   }

   dsx1FarEndIntervalIndex OBJECT-TYPE
        SYNTAX  InterfaceIndex
        MAX-ACCESS  read-only  -- read-only since originally an
        STATUS  current
        ::= { dsx1FarEndIntervalEntry 1 }

   dsx1FarEndIntervalNumber OBJECT-TYPE
        SYNTAX  INTEGER (1..96)
        MAX-ACCESS  read-only  -- read-only since originally an
        STATUS  current
        ::= { dsx1FarEndIntervalEntry 2 }

   dsx1FarEndIntervalESs OBJECT-TYPE
        SYNTAX  PerfIntervalCount
        MAX-ACCESS  read-only
        STATUS  current
        ::= { dsx1FarEndIntervalEntry 3 }

   dsx1FarEndIntervalSESs OBJECT-TYPE
        SYNTAX  PerfIntervalCount
        MAX-ACCESS  read-only
        STATUS  current
        ::= { dsx1FarEndIntervalEntry 4 }

   dsx1FarEndIntervalSEFSs OBJECT-TYPE
        SYNTAX  PerfIntervalCount
        MAX-ACCESS  read-only
        STATUS  current
        ::= { dsx1FarEndIntervalEntry 5 }

   dsx1FarEndIntervalUASs OBJECT-TYPE
        SYNTAX  PerfIntervalCount
        MAX-ACCESS  read-only
        STATUS  current
        ::= { dsx1FarEndIntervalEntry 6 }

   dsx1FarEndIntervalCSSs OBJECT-TYPE
        SYNTAX  PerfIntervalCount
        MAX-ACCESS  read-only
        STATUS  current
        ::= { dsx1FarEndIntervalEntry 7 }

   dsx1FarEndIntervalLESs OBJECT-TYPE
        SYNTAX  PerfIntervalCount
        MAX-ACCESS  read-only
        STATUS  current
        ::= { dsx1FarEndIntervalEntry 8 }

   dsx1FarEndIntervalPCVs OBJECT-TYPE
        SYNTAX  PerfIntervalCount
        MAX-ACCESS  read-only
        STATUS  current
        ::= { dsx1FarEndIntervalEntry 9 }

   dsx1FarEndIntervalBESs OBJECT-TYPE
        SYNTAX PerfIntervalCount
        MAX-ACCESS read-only
        STATUS current





        ::= { dsx1FarEndIntervalEntry 10 }

   dsx1FarEndIntervalDMs OBJECT-TYPE
        SYNTAX PerfIntervalCount
        MAX-ACCESS read-only
        STATUS deprecated
        ::= { dsx1FarEndIntervalEntry 11 }

   dsx1FarEndIntervalValidData OBJECT-TYPE
        SYNTAX TruthValue
        MAX-ACCESS read-only
        STATUS current
        ::= { dsx1FarEndIntervalEntry 12 }


   dsx1FarEndTotalTable OBJECT-TYPE
        SYNTAX  SEQUENCE OF Dsx1FarEndTotalEntry
        MAX-ACCESS  not-accessible
        STATUS  current
        ::= { ds1 12 }

   dsx1FarEndTotalEntry OBJECT-TYPE
        SYNTAX  Dsx1FarEndTotalEntry
        MAX-ACCESS  not-accessible
        STATUS  current
        INDEX   { dsx1FarEndTotalIndex }
        ::= { dsx1FarEndTotalTable 1 }

   Dsx1FarEndTotalEntry ::=
        SEQUENCE {
            dsx1FarEndTotalIndex          InterfaceIndex,
            dsx1FarEndTotalESs            PerfTotalCount,
            dsx1FarEndTotalSESs           PerfTotalCount,
            dsx1FarEndTotalSEFSs          PerfTotalCount,





            dsx1FarEndTotalUASs           PerfTotalCount,
            dsx1FarEndTotalCSSs           PerfTotalCount,
            dsx1FarEndTotalLESs           PerfTotalCount,
            dsx1FarEndTotalPCVs           PerfTotalCount,
            dsx1FarEndTotalBESs           PerfTotalCount,
            dsx1FarEndTotalDMs            PerfTotalCount
   }

   dsx1FarEndTotalIndex OBJECT-TYPE
        SYNTAX  InterfaceIndex
        MAX-ACCESS  read-only  -- read-only since originally an
        STATUS  current
        ::= { dsx1FarEndTotalEntry 1 }

   dsx1FarEndTotalESs OBJECT-TYPE
        SYNTAX  PerfTotalCount
        MAX-ACCESS  read-only
        STATUS  current
        ::= { dsx1FarEndTotalEntry 2 }

   dsx1FarEndTotalSESs OBJECT-TYPE
        SYNTAX  PerfTotalCount
        MAX-ACCESS  read-only
        STATUS  current
        ::= { dsx1FarEndTotalEntry 3 }

   dsx1FarEndTotalSEFSs OBJECT-TYPE
        SYNTAX  PerfTotalCount
        MAX-ACCESS  read-only
        STATUS  current
        ::= { dsx1FarEndTotalEntry 4 }

   dsx1FarEndTotalUASs OBJECT-TYPE
        SYNTAX  PerfTotalCount
        MAX-ACCESS  read-only
        STATUS  current
        ::= { dsx1FarEndTotalEntry 5 }

   dsx1FarEndTotalCSSs OBJECT-TYPE
        SYNTAX  PerfTotalCount
        MAX-ACCESS  read-only
        STATUS  current
        ::= { dsx1FarEndTotalEntry 6 }

   dsx1FarEndTotalLESs OBJECT-TYPE
        SYNTAX  PerfTotalCount
        MAX-ACCESS  read-only
        STATUS  current
        ::= { dsx1FarEndTotalEntry 7 }

   dsx1FarEndTotalPCVs OBJECT-TYPE
        SYNTAX  PerfTotalCount
        MAX-ACCESS  read-only
        STATUS  current





        ::= { dsx1FarEndTotalEntry 8 }

   dsx1FarEndTotalBESs OBJECT-TYPE
        SYNTAX PerfTotalCount
        MAX-ACCESS read-only
        STATUS current
        ::= { dsx1FarEndTotalEntry 9 }

   dsx1FarEndTotalDMs OBJECT-TYPE
        SYNTAX PerfTotalCount
        MAX-ACCESS read-only
        STATUS deprecated
        ::= { dsx1FarEndTotalEntry 10 }


   dsx1FracTable OBJECT-TYPE
        SYNTAX  SEQUENCE OF Dsx1FracEntry
        MAX-ACCESS  not-accessible
        STATUS  deprecated
        ::= { ds1 13 }

   dsx1FracEntry OBJECT-TYPE
        SYNTAX  Dsx1FracEntry
        MAX-ACCESS  not-accessible
        STATUS  deprecated
       INDEX   { dsx1FracIndex, dsx1FracNumber }
       ::= { dsx1FracTable 1 }





   Dsx1FracEntry ::=
       SEQUENCE {
           dsx1FracIndex        INTEGER,
           dsx1FracNumber       INTEGER,
           dsx1FracIfIndex      INTEGER
       }

   dsx1FracIndex OBJECT-TYPE
       SYNTAX  INTEGER (1..'7fffffff'h)
       MAX-ACCESS  read-only  -- read-only since originally an
       STATUS  deprecated
      ::= { dsx1FracEntry 1 }

   dsx1FracNumber OBJECT-TYPE
       SYNTAX  INTEGER (1..31)
       MAX-ACCESS  read-only  -- read-only since originally an
       STATUS  deprecated
      ::= { dsx1FracEntry 2 }

   dsx1FracIfIndex OBJECT-TYPE
       SYNTAX  INTEGER (0..'7fffffff'h)
       MAX-ACCESS  read-write
       STATUS  deprecated
      ::= { dsx1FracEntry 3 }







   ds1Traps OBJECT IDENTIFIER ::= { ds1 15 }

   dsx1LineStatusChange NOTIFICATION-TYPE
       OBJECTS { dsx1LineStatus,
                 dsx1LineStatusLastChange }
       STATUS  current
        ::= { ds1Traps 0 1 }


   ds1Conformance OBJECT IDENTIFIER ::= { ds1 14 }

   ds1Groups      OBJECT IDENTIFIER ::= { ds1Conformance 1 }
   ds1Compliances OBJECT IDENTIFIER ::= { ds1Conformance 2 }


   ds1Compliance MODULE-COMPLIANCE
       STATUS  deprecated
       MODULE  -- this module
           MANDATORY-GROUPS { ds1NearEndConfigGroup,
                              ds1NearEndStatisticsGroup }

           GROUP       ds1FarEndGroup

           GROUP       ds1NearEndOptionalConfigGroup

           GROUP       ds1DS2Group





           GROUP       ds1TransStatsGroup

           GROUP       ds1ChanMappingGroup

           OBJECT dsx1LineType
                   SYNTAX  INTEGER {
                               other(1),
                               dsx1ESF(2),
                               dsx1D4(3),
                               dsx1E1(4),
                               dsx1E1CRC(5),
                               dsx1E1MF(6),
                               dsx1E1CRCMF(7),
                               dsx1Unframed(8),
                               dsx1E1Unframed(9),
                               dsx1DS2M12(10),
                               dsx1E2(11)
                             }
           MIN-ACCESS read-only

           OBJECT dsx1LineCoding
           MIN-ACCESS read-only

           OBJECT dsx1SendCode
           MIN-ACCESS read-only

           OBJECT dsx1LoopbackConfig
           MIN-ACCESS read-only

           OBJECT dsx1SignalMode
           MIN-ACCESS read-only

           OBJECT dsx1TransmitClockSource
                   SYNTAX  INTEGER {
                                loopTiming(1),
                                localTiming(2),
                                throughTiming(3)
                              }
           MIN-ACCESS read-only

           OBJECT dsx1Fdl
           MIN-ACCESS read-only

           OBJECT dsx1LineLength
           MIN-ACCESS read-only

           OBJECT dsx1Channelization
           MIN-ACCESS read-only
       ::= { ds1Compliances 1 }

   ds1MibT1PriCompliance MODULE-COMPLIANCE
       STATUS deprecated
       MODULE
           MANDATORY-GROUPS { ds1NearEndConfigGroup,
                              ds1NearEndStatisticsGroup }
           OBJECT dsx1LineType
               SYNTAX INTEGER {
                   dsx1ESF(2)   -- Intl Spec would be G704(2)





               }
               MIN-ACCESS read-only

           OBJECT dsx1LineCoding
               SYNTAX INTEGER {
                   dsx1B8ZS(2)
               }
               MIN-ACCESS read-only

           OBJECT dsx1SignalMode
               SYNTAX INTEGER {
                   none(1), -- if there is no signaling channel
                   messageOriented(4)
               }
               MIN-ACCESS read-only

           OBJECT dsx1TransmitClockSource
               SYNTAX INTEGER {
                   loopTiming(1)
               }
               MIN-ACCESS read-only

           OBJECT dsx1Fdl
               MIN-ACCESS read-only

           OBJECT dsx1Channelization
               MIN-ACCESS read-only
       ::= { ds1Compliances 2 }

   ds1MibE1PriCompliance MODULE-COMPLIANCE
       STATUS deprecated
       MODULE
           MANDATORY-GROUPS { ds1NearEndConfigGroup,
                              ds1NearEndStatisticsGroup }
           OBJECT dsx1LineType
               SYNTAX INTEGER {
                   dsx1E1CRC(5)
               }
               MIN-ACCESS read-only

           OBJECT dsx1LineCoding
               SYNTAX INTEGER {
                   dsx1HDB3(3)
               }
               MIN-ACCESS read-only

           OBJECT dsx1SignalMode
               SYNTAX INTEGER {
                   messageOriented(4)
               }
               MIN-ACCESS read-only

           OBJECT dsx1TransmitClockSource
               SYNTAX INTEGER {
                   loopTiming(1)
               }
               MIN-ACCESS read-only

           OBJECT dsx1Fdl





               MIN-ACCESS read-only

           OBJECT dsx1Channelization
               MIN-ACCESS read-only
       ::= { ds1Compliances 3 }

   ds1Ds2Compliance MODULE-COMPLIANCE
       STATUS current
       MODULE
           MANDATORY-GROUPS { ds1DS2Group }

           OBJECT dsx1LineType
                SYNTAX INTEGER {
                           dsx1DS2M12(10),
                           dsx1E2(11)
                }
                MIN-ACCESS read-only

           OBJECT dsx1Channelization
                MIN-ACCESS read-only





       ::= { ds1Compliances 4 }

   ds1NCompliance MODULE-COMPLIANCE
       STATUS  deprecated
       MODULE  -- this module
           MANDATORY-GROUPS { ds1NearEndConfigurationGroup,
                              ds1NearEndStatisticsGroup }

           GROUP       ds1FarEndGroup

            GROUP       ds1NearEndOptionalTrapGroup

           GROUP       ds1NearEndOptionalConfigGroup

           GROUP       ds1DS2Group

           GROUP       ds1TransStatsGroup


           GROUP       ds1ChanMappingGroup





           OBJECT dsx1LineType
           MIN-ACCESS read-only

           OBJECT dsx1LineCoding
           MIN-ACCESS read-only

           OBJECT dsx1SendCode
           MIN-ACCESS read-only

           OBJECT dsx1LoopbackConfig
           MIN-ACCESS read-only

           OBJECT dsx1SignalMode
           MIN-ACCESS read-only

           OBJECT dsx1TransmitClockSource
           MIN-ACCESS read-only

           OBJECT dsx1Fdl
           MIN-ACCESS read-only

           OBJECT dsx1LineLength
           MIN-ACCESS read-only

           OBJECT dsx1Channelization
           MIN-ACCESS read-only






           OBJECT dsx1LineMode
           MIN-ACCESS read-only

           OBJECT dsx1LineBuildOut
           MIN-ACCESS read-only
       ::= { ds1Compliances 5 }

   ds1MibT1PriNCompliance MODULE-COMPLIANCE
       STATUS deprecated
       MODULE
           MANDATORY-GROUPS { ds1NearEndConfigurationGroup,
                              ds1NearEndStatisticsGroup }
           OBJECT dsx1LineType
               SYNTAX INTEGER {
                   dsx1ESF(2)   -- Intl Spec would be G704(2)
               }
               MIN-ACCESS read-only

           OBJECT dsx1LineCoding
               SYNTAX INTEGER {
                   dsx1B8ZS(2)
               }
               MIN-ACCESS read-only

           OBJECT dsx1SignalMode
               SYNTAX INTEGER {
                   none(1), -- if there is no signaling channel
                   messageOriented(4)





               }
               MIN-ACCESS read-only

           OBJECT dsx1TransmitClockSource
               SYNTAX INTEGER {
                   loopTiming(1)
               }
               MIN-ACCESS read-only

           OBJECT dsx1Fdl
               MIN-ACCESS read-only

           OBJECT dsx1Channelization
               MIN-ACCESS read-only

           OBJECT dsx1LineMode
               MIN-ACCESS read-only

           OBJECT dsx1LineBuildOut
               MIN-ACCESS read-only
       ::= { ds1Compliances 6 }

   ds1MibE1PriNCompliance MODULE-COMPLIANCE
       STATUS deprecated





       MODULE
           MANDATORY-GROUPS { ds1NearEndConfigurationGroup,
                              ds1NearEndStatisticsGroup }
           OBJECT dsx1LineType
               SYNTAX INTEGER {
                   dsx1E1CRC(5)
               }
               MIN-ACCESS read-only

           OBJECT dsx1LineCoding
               SYNTAX INTEGER {
                   dsx1HDB3(3)
               }
               MIN-ACCESS read-only

           OBJECT dsx1SignalMode
               SYNTAX INTEGER {
                   messageOriented(4)
               }
               MIN-ACCESS read-only


           OBJECT dsx1TransmitClockSource
               SYNTAX INTEGER {
                   loopTiming(1)
               }
               MIN-ACCESS read-only

           OBJECT dsx1Fdl
               MIN-ACCESS read-only

           OBJECT dsx1Channelization
               MIN-ACCESS read-only

           OBJECT dsx1LineMode
               MIN-ACCESS read-only

           OBJECT dsx1LineBuildOut
               MIN-ACCESS read-only
       ::= { ds1Compliances 7 }

   ds1J1Compliance MODULE-COMPLIANCE
       STATUS  current
       MODULE  -- this module
           MANDATORY-GROUPS { ds1NearEndCfgGroup,
                              ds1NearEndStatGroup }

           GROUP       ds1FarEndNGroup

            GROUP       ds1NearEndOptionalTrapGroup

           GROUP       ds1NearEndOptionalConfigGroup

           GROUP       ds1DS2Group

           GROUP       ds1TransStatsGroup

           GROUP       ds1ChanMappingGroup

           OBJECT dsx1LineType
           MIN-ACCESS read-only

           OBJECT dsx1LineCoding
           MIN-ACCESS read-only

           OBJECT dsx1SendCode
           MIN-ACCESS read-only

           OBJECT dsx1LoopbackConfig
           MIN-ACCESS read-only






           OBJECT dsx1SignalMode
           MIN-ACCESS read-only

           OBJECT dsx1TransmitClockSource
           MIN-ACCESS read-only

           OBJECT dsx1Fdl
           MIN-ACCESS read-only

           OBJECT dsx1LineLength
           MIN-ACCESS read-only

           OBJECT dsx1Channelization
           MIN-ACCESS read-only

           OBJECT dsx1LineMode
           MIN-ACCESS read-only

           OBJECT dsx1LineBuildOut
           MIN-ACCESS read-only

           OBJECT dsx1LineImpedance
           MIN-ACCESS read-only
       ::= { ds1Compliances 8 }

   ds1NMibT1PriNCompliance MODULE-COMPLIANCE
       STATUS current
       MODULE
           MANDATORY-GROUPS { ds1NearEndCfgGroup,
                              ds1NearEndStatGroup }
           OBJECT dsx1LineType
               SYNTAX INTEGER {
                   dsx1ESF(2)   -- Intl Spec would be G704(2)
               }
               MIN-ACCESS read-only

           OBJECT dsx1LineCoding
               SYNTAX INTEGER {
                   dsx1B8ZS(2)
               }
               MIN-ACCESS read-only

           OBJECT dsx1SignalMode
               SYNTAX INTEGER {
                   none(1), -- if there is no signaling channel
                   messageOriented(4)
               }
               MIN-ACCESS read-only

           OBJECT dsx1TransmitClockSource
               SYNTAX INTEGER {
                   loopTiming(1)
               }
               MIN-ACCESS read-only

           OBJECT dsx1Fdl
               MIN-ACCESS read-only

           OBJECT dsx1Channelization
               MIN-ACCESS read-only

           OBJECT dsx1LineMode
               MIN-ACCESS read-only

           OBJECT dsx1LineBuildOut
               MIN-ACCESS read-only
       ::= { ds1Compliances 9 }

   ds1NMibE1PriNCompliance MODULE-COMPLIANCE
       STATUS current
       MODULE
           MANDATORY-GROUPS { ds1NearEndCfgGroup,
                              ds1NearEndStatGroup }

           OBJECT dsx1LineType
               SYNTAX INTEGER {
                   dsx1E1CRC(5)
               }
               MIN-ACCESS read-only

           OBJECT dsx1LineCoding





               SYNTAX INTEGER {
                   dsx1HDB3(3)
               }
               MIN-ACCESS read-only

           OBJECT dsx1SignalMode
               SYNTAX INTEGER {
                   messageOriented(4)
               }
               MIN-ACCESS read-only

           OBJECT dsx1TransmitClockSource
               SYNTAX INTEGER {
                   loopTiming(1)
               }
               MIN-ACCESS read-only

           OBJECT dsx1Fdl
               MIN-ACCESS read-only

           OBJECT dsx1Channelization
               MIN-ACCESS read-only

           OBJECT dsx1LineMode
               MIN-ACCESS read-only

           OBJECT dsx1LineBuildOut
               MIN-ACCESS read-only

           OBJECT dsx1LineImpedance
               MIN-ACCESS read-only
        ::= { ds1Compliances 10 }


   ds1NearEndConfigGroup  OBJECT-GROUP
       OBJECTS { dsx1LineIndex,
                 dsx1TimeElapsed,
                 dsx1ValidIntervals,
                 dsx1LineType,
                 dsx1LineCoding,
                 dsx1SendCode,
                 dsx1CircuitIdentifier,
                 dsx1LoopbackConfig,
                 dsx1LineStatus,
                 dsx1SignalMode,
                 dsx1TransmitClockSource,
                 dsx1Fdl,
                 dsx1InvalidIntervals,
                 dsx1LineLength,
                 dsx1LoopbackStatus,
                 dsx1Ds1ChannelNumber,
                 dsx1Channelization                      }
       STATUS  deprecated
       ::= { ds1Groups 1 }






   ds1NearEndStatisticsGroup OBJECT-GROUP
       OBJECTS { dsx1CurrentIndex,
                 dsx1CurrentESs,
                 dsx1CurrentSESs,
                 dsx1CurrentSEFSs,
                 dsx1CurrentUASs,
                 dsx1CurrentCSSs,
                 dsx1CurrentPCVs,
                 dsx1CurrentLESs,
                 dsx1CurrentBESs,
                 dsx1CurrentDMs,
                 dsx1CurrentLCVs,
                 dsx1IntervalIndex,
                 dsx1IntervalNumber,
                 dsx1IntervalESs,
                 dsx1IntervalSESs,
                 dsx1IntervalSEFSs,
                 dsx1IntervalUASs,
                 dsx1IntervalCSSs,
                 dsx1IntervalPCVs,
                 dsx1IntervalLESs,
                 dsx1IntervalBESs,
                 dsx1IntervalDMs,
                 dsx1IntervalLCVs,
                 dsx1IntervalValidData,
                 dsx1TotalIndex,
                 dsx1TotalESs,
                 dsx1TotalSESs,
                 dsx1TotalSEFSs,
                 dsx1TotalUASs,
                 dsx1TotalCSSs,
                 dsx1TotalPCVs,
                 dsx1TotalLESs,
                 dsx1TotalBESs,
                 dsx1TotalDMs,
                 dsx1TotalLCVs }
       STATUS  deprecated
       ::= { ds1Groups 2 }

   ds1FarEndGroup  OBJECT-GROUP
       OBJECTS { dsx1FarEndCurrentIndex,
                 dsx1FarEndTimeElapsed,
                 dsx1FarEndValidIntervals,
                 dsx1FarEndCurrentESs,
                 dsx1FarEndCurrentSESs,





                 dsx1FarEndCurrentSEFSs,
                 dsx1FarEndCurrentUASs,
                 dsx1FarEndCurrentCSSs,
                 dsx1FarEndCurrentLESs,
                 dsx1FarEndCurrentPCVs,
                 dsx1FarEndCurrentBESs,
                 dsx1FarEndCurrentDMs,
                 dsx1FarEndInvalidIntervals,
                 dsx1FarEndIntervalIndex,
                 dsx1FarEndIntervalNumber,
                 dsx1FarEndIntervalESs,
                 dsx1FarEndIntervalSESs,
                 dsx1FarEndIntervalSEFSs,
                 dsx1FarEndIntervalUASs,
                 dsx1FarEndIntervalCSSs,
                 dsx1FarEndIntervalLESs,
                 dsx1FarEndIntervalPCVs,
                 dsx1FarEndIntervalBESs,
                 dsx1FarEndIntervalDMs,
                 dsx1FarEndIntervalValidData,
                 dsx1FarEndTotalIndex,
                 dsx1FarEndTotalESs,
                 dsx1FarEndTotalSESs,
                 dsx1FarEndTotalSEFSs,
                 dsx1FarEndTotalUASs,
                 dsx1FarEndTotalCSSs,
                 dsx1FarEndTotalLESs,
                 dsx1FarEndTotalPCVs,
                 dsx1FarEndTotalBESs,
                 dsx1FarEndTotalDMs }
       STATUS  deprecated
       ::= { ds1Groups 3 }

   ds1DeprecatedGroup OBJECT-GROUP
       OBJECTS { dsx1IfIndex,
                 dsx1FracIndex,
                 dsx1FracNumber,
                 dsx1FracIfIndex }
       STATUS  deprecated
       ::= { ds1Groups 4 }

   ds1NearEndOptionalConfigGroup OBJECT-GROUP





       OBJECTS { dsx1LineStatusLastChange,
                 dsx1LineStatusChangeTrapEnable }

       STATUS    current
       ::= { ds1Groups 5 }

   ds1DS2Group OBJECT-GROUP
       OBJECTS { dsx1LineIndex,
                 dsx1LineType,
                 dsx1LineCoding,
                 dsx1SendCode,
                 dsx1LineStatus,
                 dsx1SignalMode,
                 dsx1TransmitClockSource,
                 dsx1Channelization }
       STATUS   current
       ::= { ds1Groups 6 }

   ds1TransStatsGroup OBJECT-GROUP
       OBJECTS { dsx1CurrentESs,
                 dsx1CurrentSESs,
                 dsx1CurrentUASs,
                 dsx1IntervalESs,
                 dsx1IntervalSESs,
                 dsx1IntervalUASs,
                 dsx1TotalESs,
                 dsx1TotalSESs,
                 dsx1TotalUASs }
       STATUS   current
       ::= { ds1Groups 7 }

   ds1NearEndOptionalTrapGroup NOTIFICATION-GROUP
       NOTIFICATIONS { dsx1LineStatusChange }
       STATUS    current
       ::= { ds1Groups 8 }

   ds1ChanMappingGroup OBJECT-GROUP
       OBJECTS { dsx1ChanMappedIfIndex }
       STATUS    current
       ::= { ds1Groups 9 }

   ds1NearEndConfigurationGroup  OBJECT-GROUP
       OBJECTS { dsx1LineIndex,
                 dsx1TimeElapsed,
                 dsx1ValidIntervals,
                 dsx1LineType,
                 dsx1LineCoding,
                 dsx1SendCode,
                 dsx1CircuitIdentifier,
                 dsx1LoopbackConfig,
                 dsx1LineStatus,
                 dsx1SignalMode,
                 dsx1TransmitClockSource,
                 dsx1Fdl,
                 dsx1InvalidIntervals,
                 dsx1LineLength,
                 dsx1LoopbackStatus,
                 dsx1Ds1ChannelNumber,
                 dsx1Channelization,
                 dsx1LineMode,
                 dsx1LineBuildOut                      }
       STATUS  deprecated
       ::= { ds1Groups 10 }

   ds1NearEndCfgGroup  OBJECT-GROUP
       OBJECTS { dsx1LineIndex,
                 dsx1TimeElapsed,
                 dsx1ValidIntervals,
                 dsx1LineType,
                 dsx1LineCoding,
                 dsx1SendCode,
                 dsx1CircuitIdentifier,
                 dsx1LoopbackConfig,
                 dsx1LineStatus,





                 dsx1SignalMode,
                 dsx1TransmitClockSource,
                 dsx1Fdl,
                 dsx1InvalidIntervals,
                 dsx1LineLength,
                 dsx1LoopbackStatus,
                 dsx1Ds1ChannelNumber,
                 dsx1Channelization,
                 dsx1LineMode,
                 dsx1LineBuildOut,
                 dsx1LineImpedance                     }
       STATUS  current
       ::= { ds1Groups 11 }

   ds1NearEndStatGroup OBJECT-GROUP
       OBJECTS { dsx1CurrentIndex,
                 dsx1CurrentESs,
                 dsx1CurrentSESs,
                 dsx1CurrentSEFSs,
                 dsx1CurrentUASs,
                 dsx1CurrentCSSs,
                 dsx1CurrentPCVs,
                 dsx1CurrentLESs,
                 dsx1CurrentBESs,
                 dsx1CurrentLCVs,
                 dsx1IntervalIndex,
                 dsx1IntervalNumber,
                 dsx1IntervalESs,
                 dsx1IntervalSESs,
                 dsx1IntervalSEFSs,
                 dsx1IntervalUASs,
                 dsx1IntervalCSSs,
                 dsx1IntervalPCVs,
                 dsx1IntervalLESs,
                 dsx1IntervalBESs,
                 dsx1IntervalLCVs,
                 dsx1IntervalValidData,
                 dsx1TotalIndex,
                 dsx1TotalESs,
                 dsx1TotalSESs,
                 dsx1TotalSEFSs,
                 dsx1TotalUASs,
                 dsx1TotalCSSs,
                 dsx1TotalPCVs,
                 dsx1TotalLESs,





                 dsx1TotalBESs,
                 dsx1TotalLCVs }
       STATUS  current
       ::= { ds1Groups 12 }

   ds1FarEndNGroup  OBJECT-GROUP
       OBJECTS { dsx1FarEndCurrentIndex,
                 dsx1FarEndTimeElapsed,
                 dsx1FarEndValidIntervals,
                 dsx1FarEndCurrentESs,
                 dsx1FarEndCurrentSESs,
                 dsx1FarEndCurrentSEFSs,
                 dsx1FarEndCurrentUASs,
                 dsx1FarEndCurrentCSSs,
                 dsx1FarEndCurrentLESs,
                 dsx1FarEndCurrentPCVs,
                 dsx1FarEndCurrentBESs,
                 dsx1FarEndInvalidIntervals,
                 dsx1FarEndIntervalIndex,
                 dsx1FarEndIntervalNumber,
                 dsx1FarEndIntervalESs,
                 dsx1FarEndIntervalSESs,
                 dsx1FarEndIntervalSEFSs,
                 dsx1FarEndIntervalUASs,
                 dsx1FarEndIntervalCSSs,
                 dsx1FarEndIntervalLESs,
                 dsx1FarEndIntervalPCVs,
                 dsx1FarEndIntervalBESs,
                 dsx1FarEndIntervalValidData,
                 dsx1FarEndTotalIndex,
                 dsx1FarEndTotalESs,
                 dsx1FarEndTotalSESs,
                 dsx1FarEndTotalSEFSs,
                 dsx1FarEndTotalUASs,
                 dsx1FarEndTotalCSSs,
                 dsx1FarEndTotalLESs,
                 dsx1FarEndTotalPCVs,
                 dsx1FarEndTotalBESs}
       STATUS  current
       ::= { ds1Groups 13 }
   END
