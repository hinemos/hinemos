DS0-MIB DEFINITIONS ::= BEGIN

   IMPORTS
        MODULE-IDENTITY, OBJECT-TYPE,
        transmission                     FROM SNMPv2-SMI
        MODULE-COMPLIANCE, OBJECT-GROUP  FROM SNMPv2-CONF
        DisplayString, TruthValue        FROM SNMPv2-TC
        ifIndex, InterfaceIndex,
        InterfaceIndexOrZero             FROM IF-MIB;


   ds0 MODULE-IDENTITY
       LAST-UPDATED "9807161630Z"
       ORGANIZATION "IETF Trunk MIB Working Group"

       ::= { transmission 81 }





   dsx0ConfigTable OBJECT-TYPE
       SYNTAX  SEQUENCE OF Dsx0ConfigEntry
       MAX-ACCESS  not-accessible
       STATUS  current
       ::= { ds0 1 }

   dsx0ConfigEntry OBJECT-TYPE
       SYNTAX  Dsx0ConfigEntry
       MAX-ACCESS  not-accessible
       STATUS  current
       INDEX   { ifIndex }
       ::= { dsx0ConfigTable 1 }

   Dsx0ConfigEntry ::=
       SEQUENCE {
           dsx0Ds0ChannelNumber        INTEGER,
           dsx0RobbedBitSignalling     TruthValue,
           dsx0CircuitIdentifier       DisplayString,
           dsx0IdleCode                INTEGER,
           dsx0SeizedCode              INTEGER,





           dsx0ReceivedCode            INTEGER,
           dsx0TransmitCodesEnable     TruthValue,
           dsx0Ds0BundleMappedIfIndex  InterfaceIndexOrZero
   }

   dsx0Ds0ChannelNumber OBJECT-TYPE
       SYNTAX  INTEGER(0..31)
       MAX-ACCESS  read-only
       STATUS  current
       ::= { dsx0ConfigEntry 1 }

   dsx0RobbedBitSignalling OBJECT-TYPE
       SYNTAX  TruthValue
       MAX-ACCESS  read-write
       STATUS  current
       ::= { dsx0ConfigEntry 2 }

   dsx0CircuitIdentifier OBJECT-TYPE
        SYNTAX  DisplayString (SIZE (0..255))
        MAX-ACCESS  read-write
        STATUS  current
       ::= { dsx0ConfigEntry 3 }

   dsx0IdleCode OBJECT-TYPE
        SYNTAX  INTEGER(0..15)
        MAX-ACCESS  read-write
        STATUS  current





       ::= { dsx0ConfigEntry 4 }

   dsx0SeizedCode OBJECT-TYPE
        SYNTAX  INTEGER(0..15)
        MAX-ACCESS  read-write
        STATUS  current
       ::= { dsx0ConfigEntry 5 }

   dsx0ReceivedCode OBJECT-TYPE
        SYNTAX  INTEGER(0..15)
        MAX-ACCESS  read-only
        STATUS  current
       ::= { dsx0ConfigEntry 6 }

   dsx0TransmitCodesEnable OBJECT-TYPE
        SYNTAX TruthValue
        MAX-ACCESS  read-write
        STATUS  current
       ::= { dsx0ConfigEntry 7 }

   dsx0Ds0BundleMappedIfIndex OBJECT-TYPE
        SYNTAX InterfaceIndexOrZero
        MAX-ACCESS  read-only
        STATUS  current
       ::= { dsx0ConfigEntry 8 }


   dsx0ChanMappingTable OBJECT-TYPE
        SYNTAX  SEQUENCE OF Dsx0ChanMappingEntry
        MAX-ACCESS  not-accessible
        STATUS  current
        ::= { ds0 3 }

   dsx0ChanMappingEntry OBJECT-TYPE
        SYNTAX  Dsx0ChanMappingEntry
        MAX-ACCESS  not-accessible
        STATUS  current
        INDEX   { ifIndex, dsx0Ds0ChannelNumber }
        ::= { dsx0ChanMappingTable 1 }

   Dsx0ChanMappingEntry ::=
        SEQUENCE {
            dsx0ChanMappedIfIndex  InterfaceIndex
   }

   dsx0ChanMappedIfIndex OBJECT-TYPE
        SYNTAX  InterfaceIndex
        MAX-ACCESS  read-only
        STATUS  current
        ::= { dsx0ChanMappingEntry 1 }


   ds0Conformance OBJECT IDENTIFIER ::= { ds0 2 }

   ds0Groups      OBJECT IDENTIFIER ::= { ds0Conformance 1 }
   ds0Compliances OBJECT IDENTIFIER ::= { ds0Conformance 2 }




   ds0Compliance MODULE-COMPLIANCE
       STATUS  current
       MODULE  -- this module
           MANDATORY-GROUPS { ds0ConfigGroup }

           OBJECT dsx0RobbedBitSignalling
           MIN-ACCESS read-only
           OBJECT dsx0CircuitIdentifier
           MIN-ACCESS read-only

           OBJECT dsx0IdleCode
           MIN-ACCESS read-only

           OBJECT dsx0SeizedCode
           MIN-ACCESS read-only

           OBJECT dsx0TransmitCodesEnable
           MIN-ACCESS read-only

       ::= { ds0Compliances 1 }


   ds0ConfigGroup  OBJECT-GROUP
       OBJECTS { dsx0Ds0ChannelNumber,
                 dsx0RobbedBitSignalling,
                 dsx0CircuitIdentifier,
                 dsx0IdleCode,
                 dsx0SeizedCode,
                 dsx0ReceivedCode,
                 dsx0TransmitCodesEnable,
                 dsx0Ds0BundleMappedIfIndex,
                 dsx0ChanMappedIfIndex }
       STATUS  current
       ::= { ds0Groups 1 }

   END
