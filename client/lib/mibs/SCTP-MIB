SCTP-MIB DEFINITIONS ::= BEGIN

   IMPORTS
     MODULE-IDENTITY, OBJECT-TYPE, Integer32, Unsigned32, Gauge32,
     Counter32, Counter64, mib-2
          FROM SNMPv2-SMI                        -- [RFC2578]
     TimeStamp, TruthValue
          FROM SNMPv2-TC                         -- [RFC2579]
     MODULE-COMPLIANCE, OBJECT-GROUP
          FROM SNMPv2-CONF                       -- [RFC2580]
     InetAddressType, InetAddress, InetPortNumber
          FROM INET-ADDRESS-MIB;                 -- [RFC3291]









   sctpMIB MODULE-IDENTITY
     LAST-UPDATED "200409020000Z"       -- 2nd September 2004
     ORGANIZATION "IETF SIGTRAN Working Group"



     ::= {  mib-2 104 }






   sctpObjects OBJECT IDENTIFIER ::= { sctpMIB 1 }

   sctpStats   OBJECT IDENTIFIER ::= { sctpObjects 1 }
   sctpParams  OBJECT IDENTIFIER ::= { sctpObjects 2 }



   sctpCurrEstab OBJECT-TYPE
     SYNTAX         Gauge32
     MAX-ACCESS     read-only
     STATUS         current

     ::= { sctpStats 1 }


   sctpActiveEstabs OBJECT-TYPE
     SYNTAX         Counter32
     MAX-ACCESS     read-only
     STATUS         current

     ::= { sctpStats  2 }













   sctpPassiveEstabs OBJECT-TYPE
     SYNTAX         Counter32
     MAX-ACCESS     read-only
     STATUS         current

     ::= { sctpStats  3 }


   sctpAborteds OBJECT-TYPE
     SYNTAX         Counter32
     MAX-ACCESS     read-only
     STATUS         current

     ::= { sctpStats  4 }


   sctpShutdowns OBJECT-TYPE
     SYNTAX         Counter32
     MAX-ACCESS     read-only
     STATUS         current

     ::= { sctpStats  5 }








   sctpOutOfBlues OBJECT-TYPE
     SYNTAX         Counter32
     MAX-ACCESS     read-only
     STATUS         current

     ::= { sctpStats  6 }

   sctpChecksumErrors OBJECT-TYPE
     SYNTAX         Counter32
     MAX-ACCESS     read-only
     STATUS         current

   ::= { sctpStats  7 }

   sctpOutCtrlChunks OBJECT-TYPE
     SYNTAX         Counter64
     MAX-ACCESS     read-only
     STATUS         current

     ::= { sctpStats  8 }








   sctpOutOrderChunks OBJECT-TYPE
     SYNTAX         Counter64
     MAX-ACCESS     read-only
     STATUS         current

     ::= { sctpStats  9 }

   sctpOutUnorderChunks OBJECT-TYPE
     SYNTAX         Counter64
     MAX-ACCESS     read-only
     STATUS         current

     ::= { sctpStats  10 }

   sctpInCtrlChunks OBJECT-TYPE
     SYNTAX         Counter64
     MAX-ACCESS     read-only
     STATUS         current

     ::= { sctpStats  11 }


   sctpInOrderChunks OBJECT-TYPE
     SYNTAX         Counter64
     MAX-ACCESS     read-only
     STATUS         current








     ::= { sctpStats  12 }


   sctpInUnorderChunks OBJECT-TYPE
     SYNTAX         Counter64
     MAX-ACCESS     read-only
     STATUS         current

     ::= { sctpStats  13 }



   sctpFragUsrMsgs OBJECT-TYPE
     SYNTAX         Counter64
     MAX-ACCESS     read-only
     STATUS         current

     ::= { sctpStats  14 }


   sctpReasmUsrMsgs OBJECT-TYPE
     SYNTAX         Counter64
     MAX-ACCESS     read-only
     STATUS         current

     ::= { sctpStats  15 }









   sctpOutSCTPPacks OBJECT-TYPE
     SYNTAX         Counter64
     MAX-ACCESS     read-only
     STATUS         current

     ::= { sctpStats  16 }


   sctpInSCTPPacks OBJECT-TYPE
     SYNTAX         Counter64
     MAX-ACCESS     read-only
     STATUS         current

     ::= { sctpStats  17 }

   sctpDiscontinuityTime OBJECT-TYPE
     SYNTAX         TimeStamp
     MAX-ACCESS     read-only
     STATUS         current

     ::= { sctpStats 18 }



   sctpRtoAlgorithm OBJECT-TYPE
     SYNTAX         INTEGER {
                         other(1),      -- Other new one. Future use
                         vanj(2)        -- Van Jacobson's algorithm
                    }





     MAX-ACCESS     read-only
     STATUS         current
     DEFVAL {vanj} -- vanj(2)

     ::= { sctpParams 1 }


   sctpRtoMin OBJECT-TYPE
     SYNTAX         Unsigned32
     UNITS          "milliseconds"
     MAX-ACCESS     read-only
     STATUS         current
     DEFVAL {1000} -- milliseconds

     ::= { sctpParams 2 }

   sctpRtoMax OBJECT-TYPE
     SYNTAX         Unsigned32
     UNITS          "milliseconds"
     MAX-ACCESS     read-only
     STATUS         current
     DEFVAL {60000} -- milliseconds

       ::= { sctpParams 3 }


   sctpRtoInitial OBJECT-TYPE
     SYNTAX         Unsigned32
     UNITS          "milliseconds"
     MAX-ACCESS     read-only
     STATUS         current
     DEFVAL {3000} -- milliseconds

     ::= { sctpParams 4 }


   sctpMaxAssocs OBJECT-TYPE
     SYNTAX         Integer32 (-1 | 0..2147483647)
     MAX-ACCESS     read-only
     STATUS         current

     ::= { sctpParams 5 }


   sctpValCookieLife OBJECT-TYPE
     SYNTAX         Unsigned32
     UNITS          "milliseconds"

     MAX-ACCESS     read-only
     STATUS         current
     DEFVAL {60000} -- milliseconds

     ::= { sctpParams 6 }





   sctpMaxInitRetr OBJECT-TYPE
     SYNTAX         Unsigned32
     MAX-ACCESS     read-only
     STATUS         current
     DEFVAL {8} -- number of attempts

     ::= { sctpParams 7 }






   sctpAssocTable OBJECT-TYPE
     SYNTAX         SEQUENCE OF SctpAssocEntry
     MAX-ACCESS     not-accessible
     STATUS         current

     ::= { sctpObjects 3 }


   sctpAssocEntry OBJECT-TYPE
     SYNTAX         SctpAssocEntry
     MAX-ACCESS     not-accessible

     STATUS         current
     INDEX          { sctpAssocId }

     ::= { sctpAssocTable 1 }








   SctpAssocEntry ::= SEQUENCE {
     sctpAssocId                        Unsigned32,
     sctpAssocRemHostName               OCTET STRING,
     sctpAssocLocalPort                 InetPortNumber,
     sctpAssocRemPort                   InetPortNumber,
     sctpAssocRemPrimAddrType           InetAddressType,
     sctpAssocRemPrimAddr               InetAddress,
     sctpAssocHeartBeatInterval         Unsigned32,
     sctpAssocState                     INTEGER,
     sctpAssocInStreams                 Unsigned32,
     sctpAssocOutStreams                Unsigned32,
     sctpAssocMaxRetr                   Unsigned32,
     sctpAssocPrimProcess               Unsigned32,
     sctpAssocT1expireds                Counter32,     -- Statistic
     sctpAssocT2expireds                Counter32,     -- Statistic
     sctpAssocRtxChunks                 Counter32,     -- Statistic
     sctpAssocStartTime                 TimeStamp,
     sctpAssocDiscontinuityTime         TimeStamp
     }


   sctpAssocId OBJECT-TYPE
     SYNTAX         Unsigned32 (1..4294967295)
     MAX-ACCESS     not-accessible
     STATUS         current

     ::= { sctpAssocEntry 1 }


   sctpAssocRemHostName OBJECT-TYPE
     SYNTAX         OCTET STRING (SIZE(0..255))
     MAX-ACCESS     read-only
     STATUS         current





     ::= { sctpAssocEntry 2 }


   sctpAssocLocalPort OBJECT-TYPE
     SYNTAX         InetPortNumber (1..65535)
     MAX-ACCESS     read-only
     STATUS         current

     ::= { sctpAssocEntry 3 }


   sctpAssocRemPort OBJECT-TYPE
     SYNTAX         InetPortNumber (1..65535)
     MAX-ACCESS     read-only
     STATUS         current

     ::= { sctpAssocEntry 4 }


   sctpAssocRemPrimAddrType OBJECT-TYPE
     SYNTAX         InetAddressType
     MAX-ACCESS     read-only
     STATUS         current

     ::= { sctpAssocEntry 5 }

   sctpAssocRemPrimAddr OBJECT-TYPE
     SYNTAX         InetAddress
     MAX-ACCESS     read-only
     STATUS         current

     ::= { sctpAssocEntry 6 }







   sctpAssocHeartBeatInterval OBJECT-TYPE
     SYNTAX         Unsigned32
     UNITS          "milliseconds"
     MAX-ACCESS     read-only
     STATUS         current
     DEFVAL {30000} -- milliseconds

     ::= { sctpAssocEntry 7 }


   sctpAssocState OBJECT-TYPE
     SYNTAX         INTEGER {
                         closed(1),
                         cookieWait(2),
                         cookieEchoed(3),
                         established(4),
                         shutdownPending(5),
                         shutdownSent(6),
                         shutdownReceived(7),
                         shutdownAckSent(8),
                         deleteTCB(9)
                         }
     MAX-ACCESS     read-write
     STATUS         current








     ::= { sctpAssocEntry 8 }


   sctpAssocInStreams OBJECT-TYPE
     SYNTAX         Unsigned32 (1..65535)
     MAX-ACCESS     read-only
     STATUS         current

     ::= { sctpAssocEntry 9 }

   sctpAssocOutStreams OBJECT-TYPE
     SYNTAX         Unsigned32 (1..65535)
     MAX-ACCESS     read-only
     STATUS         current

     ::= { sctpAssocEntry 10 }


   sctpAssocMaxRetr OBJECT-TYPE
     SYNTAX         Unsigned32
     MAX-ACCESS     read-only
     STATUS         current
     DEFVAL {10} -- number of attempts

     ::= { sctpAssocEntry 11 }

   sctpAssocPrimProcess OBJECT-TYPE
         SYNTAX      Unsigned32
         MAX-ACCESS read-only
         STATUS      current

     ::= { sctpAssocEntry 12 }



   sctpAssocT1expireds OBJECT-TYPE
     SYNTAX         Counter32
     MAX-ACCESS     read-only
     STATUS         current


     ::= { sctpAssocEntry 13 }

   sctpAssocT2expireds OBJECT-TYPE
     SYNTAX         Counter32
     MAX-ACCESS     read-only





     STATUS         current
     ::= { sctpAssocEntry 14 }


   sctpAssocRtxChunks OBJECT-TYPE
     SYNTAX         Counter32
     MAX-ACCESS     read-only
     STATUS         current

     ::= { sctpAssocEntry 15 }


   sctpAssocStartTime OBJECT-TYPE
     SYNTAX         TimeStamp
     MAX-ACCESS     read-only
     STATUS         current

     ::= { sctpAssocEntry 16 }

   sctpAssocDiscontinuityTime OBJECT-TYPE
     SYNTAX         TimeStamp
     MAX-ACCESS     read-only
     STATUS         current

     ::= { sctpAssocEntry 17 }



   sctpAssocLocalAddrTable OBJECT-TYPE
     SYNTAX         SEQUENCE OF SctpAssocLocalAddrEntry
     MAX-ACCESS     not-accessible
     STATUS         current

     ::= { sctpObjects  4 }

   sctpAssocLocalAddrEntry OBJECT-TYPE
     SYNTAX         SctpAssocLocalAddrEntry
     MAX-ACCESS     not-accessible
     STATUS         current
     INDEX     {    sctpAssocId,   -- shared index
                    sctpAssocLocalAddrType,
                    sctpAssocLocalAddr }

     ::= { sctpAssocLocalAddrTable 1 }


   SctpAssocLocalAddrEntry ::= SEQUENCE {
     sctpAssocLocalAddrType        InetAddressType,
     sctpAssocLocalAddr            InetAddress,
     sctpAssocLocalAddrStartTime   TimeStamp
     }


   sctpAssocLocalAddrType OBJECT-TYPE
     SYNTAX         InetAddressType
     MAX-ACCESS     not-accessible
     STATUS         current


     ::= { sctpAssocLocalAddrEntry 1 }

   sctpAssocLocalAddr OBJECT-TYPE
     SYNTAX         InetAddress
     MAX-ACCESS     not-accessible
     STATUS         current

     ::= { sctpAssocLocalAddrEntry 2 }













   sctpAssocLocalAddrStartTime OBJECT-TYPE
     SYNTAX         TimeStamp
     MAX-ACCESS     read-only
     STATUS         current

     ::= { sctpAssocLocalAddrEntry 3 }


   sctpAssocRemAddrTable OBJECT-TYPE
     SYNTAX         SEQUENCE OF SctpAssocRemAddrEntry
     MAX-ACCESS     not-accessible
     STATUS         current

     ::= { sctpObjects  5 }


   sctpAssocRemAddrEntry OBJECT-TYPE
     SYNTAX         SctpAssocRemAddrEntry
     MAX-ACCESS     not-accessible
     STATUS         current
     INDEX   { sctpAssocId,   -- shared index
               sctpAssocRemAddrType,
               sctpAssocRemAddr }

     ::= { sctpAssocRemAddrTable 1 }









   SctpAssocRemAddrEntry ::= SEQUENCE {
     sctpAssocRemAddrType               InetAddressType,
     sctpAssocRemAddr                   InetAddress,
     sctpAssocRemAddrActive             TruthValue,
     sctpAssocRemAddrHBActive           TruthValue,
     sctpAssocRemAddrRTO                Unsigned32,
     sctpAssocRemAddrMaxPathRtx         Unsigned32,
     sctpAssocRemAddrRtx                Counter32,     -- Statistic
     sctpAssocRemAddrStartTime          TimeStamp
     }


   sctpAssocRemAddrType OBJECT-TYPE
     SYNTAX         InetAddressType
     MAX-ACCESS     not-accessible
     STATUS         current
     ::= { sctpAssocRemAddrEntry 1 }


   sctpAssocRemAddr OBJECT-TYPE
     SYNTAX         InetAddress
     MAX-ACCESS     not-accessible
     STATUS         current

     ::= { sctpAssocRemAddrEntry 2 }


   sctpAssocRemAddrActive OBJECT-TYPE
     SYNTAX         TruthValue
     MAX-ACCESS     read-only
     STATUS         current


     ::= { sctpAssocRemAddrEntry 3 }


   sctpAssocRemAddrHBActive OBJECT-TYPE
     SYNTAX         TruthValue
     MAX-ACCESS     read-only
     STATUS         current

     ::= { sctpAssocRemAddrEntry 4 }


   sctpAssocRemAddrRTO OBJECT-TYPE -- T3-rtx- Timer
     SYNTAX         Unsigned32
     UNITS          "milliseconds"
     MAX-ACCESS     read-only
     STATUS         current

     ::= { sctpAssocRemAddrEntry 5 }


   sctpAssocRemAddrMaxPathRtx OBJECT-TYPE
     SYNTAX         Unsigned32
     MAX-ACCESS     read-only
     STATUS         current






     DEFVAL {5} -- number of attempts

     ::= { sctpAssocRemAddrEntry 6 }



   sctpAssocRemAddrRtx OBJECT-TYPE
     SYNTAX         Counter32
     MAX-ACCESS     read-only
     STATUS         current

     ::= { sctpAssocRemAddrEntry 7 }

   sctpAssocRemAddrStartTime OBJECT-TYPE
     SYNTAX         TimeStamp
     MAX-ACCESS     read-only
     STATUS         current

     ::= { sctpAssocRemAddrEntry 8 }



   sctpLookupLocalPortTable OBJECT-TYPE
     SYNTAX         SEQUENCE OF SctpLookupLocalPortEntry
     MAX-ACCESS     not-accessible
     STATUS         current

     ::= { sctpObjects  6 }


   sctpLookupLocalPortEntry OBJECT-TYPE
     SYNTAX         SctpLookupLocalPortEntry
     MAX-ACCESS     not-accessible
     STATUS         current

     INDEX         { sctpAssocLocalPort,
                    sctpAssocId }

     ::= { sctpLookupLocalPortTable 1 }


   SctpLookupLocalPortEntry::= SEQUENCE {
     sctpLookupLocalPortStartTime            TimeStamp
     }


   sctpLookupLocalPortStartTime OBJECT-TYPE
     SYNTAX         TimeStamp
     MAX-ACCESS     read-only
     STATUS         current

     ::= { sctpLookupLocalPortEntry 1 }


   sctpLookupRemPortTable OBJECT-TYPE
     SYNTAX         SEQUENCE OF SctpLookupRemPortEntry
     MAX-ACCESS     not-accessible
     STATUS         current










     ::= { sctpObjects  7 }

   sctpLookupRemPortEntry OBJECT-TYPE
     SYNTAX         SctpLookupRemPortEntry
     MAX-ACCESS     not-accessible
     STATUS         current

     INDEX         { sctpAssocRemPort,
                    sctpAssocId }

     ::= { sctpLookupRemPortTable 1 }

   SctpLookupRemPortEntry::= SEQUENCE {
     sctpLookupRemPortStartTime              TimeStamp
     }


   sctpLookupRemPortStartTime OBJECT-TYPE
     SYNTAX         TimeStamp
     MAX-ACCESS     read-only
     STATUS         current

     ::= { sctpLookupRemPortEntry 1 }


   sctpLookupRemHostNameTable OBJECT-TYPE
     SYNTAX         SEQUENCE OF SctpLookupRemHostNameEntry
     MAX-ACCESS     not-accessible
     STATUS         current






     ::= { sctpObjects  8 }


   sctpLookupRemHostNameEntry OBJECT-TYPE
     SYNTAX         SctpLookupRemHostNameEntry
     MAX-ACCESS     not-accessible
     STATUS         current

     INDEX         { sctpAssocRemHostName,
                    sctpAssocId }

     ::= { sctpLookupRemHostNameTable 1 }


   SctpLookupRemHostNameEntry::= SEQUENCE {
     sctpLookupRemHostNameStartTime               TimeStamp
     }

   sctpLookupRemHostNameStartTime OBJECT-TYPE
     SYNTAX         TimeStamp
     MAX-ACCESS     read-only
     STATUS         current

     ::= { sctpLookupRemHostNameEntry 1 }














   sctpLookupRemPrimIPAddrTable OBJECT-TYPE
     SYNTAX         SEQUENCE OF SctpLookupRemPrimIPAddrEntry
     MAX-ACCESS     not-accessible
     STATUS         current

     ::= { sctpObjects  9 }


   sctpLookupRemPrimIPAddrEntry OBJECT-TYPE
     SYNTAX         SctpLookupRemPrimIPAddrEntry
     MAX-ACCESS     not-accessible
     STATUS         current

     INDEX         { sctpAssocRemPrimAddrType,
                    sctpAssocRemPrimAddr,
                    sctpAssocId }

     ::= { sctpLookupRemPrimIPAddrTable 1 }

   SctpLookupRemPrimIPAddrEntry::= SEQUENCE {
     sctpLookupRemPrimIPAddrStartTime             TimeStamp
     }


   sctpLookupRemPrimIPAddrStartTime OBJECT-TYPE
     SYNTAX         TimeStamp
     MAX-ACCESS     read-only
     STATUS         current










     ::= { sctpLookupRemPrimIPAddrEntry 1 }



   sctpLookupRemIPAddrTable OBJECT-TYPE
     SYNTAX         SEQUENCE OF SctpLookupRemIPAddrEntry
     MAX-ACCESS     not-accessible
     STATUS         current

     ::= { sctpObjects  10 }


   sctpLookupRemIPAddrEntry OBJECT-TYPE
     SYNTAX         SctpLookupRemIPAddrEntry
     MAX-ACCESS     not-accessible
     STATUS         current

     INDEX         { sctpAssocRemAddrType,
                    sctpAssocRemAddr,
                    sctpAssocId }

     ::= { sctpLookupRemIPAddrTable 1 }


   SctpLookupRemIPAddrEntry::= SEQUENCE {

     sctpLookupRemIPAddrStartTime            TimeStamp
     }








   sctpLookupRemIPAddrStartTime OBJECT-TYPE
     SYNTAX         TimeStamp
     MAX-ACCESS     read-only
     STATUS         current

     ::= { sctpLookupRemIPAddrEntry 1 }



   sctpMibConformance    OBJECT IDENTIFIER ::= { sctpMIB 2 }
   sctpMibCompliances    OBJECT IDENTIFIER ::= { sctpMibConformance 1 }
   sctpMibGroups         OBJECT IDENTIFIER ::= { sctpMibConformance 2 }




   sctpLayerParamsGroup OBJECT-GROUP
     OBJECTS   { sctpRtoAlgorithm,
                 sctpRtoMin,
                 sctpRtoMax,
                 sctpRtoInitial,
                 sctpMaxAssocs,
                 sctpValCookieLife,
                 sctpMaxInitRetr
               }

     STATUS    current

     ::= { sctpMibGroups 1 }









   sctpStatsGroup OBJECT-GROUP
     OBJECTS   { sctpCurrEstab,
                 sctpActiveEstabs,
                 sctpPassiveEstabs,
                 sctpAborteds,
                 sctpShutdowns,
                 sctpOutOfBlues,
                 sctpChecksumErrors,
                 sctpOutCtrlChunks,
                 sctpOutOrderChunks,
                 sctpOutUnorderChunks,
                 sctpInCtrlChunks,
                 sctpInOrderChunks,
                 sctpInUnorderChunks,
                 sctpFragUsrMsgs,
                 sctpReasmUsrMsgs,
                 sctpOutSCTPPacks,
                 sctpInSCTPPacks,
                 sctpDiscontinuityTime,
                 sctpAssocT1expireds,
                 sctpAssocT2expireds,
                 sctpAssocRtxChunks,
                 sctpAssocRemAddrRtx
               }

     STATUS    current

     ::= { sctpMibGroups 2 }


   sctpPerAssocParamsGroup OBJECT-GROUP
     OBJECTS   { sctpAssocRemHostName,
                 sctpAssocLocalPort,
                 sctpAssocRemPort,
                 sctpAssocRemPrimAddrType,
                 sctpAssocRemPrimAddr,
                 sctpAssocHeartBeatInterval,
                 sctpAssocState,
                 sctpAssocInStreams,
                 sctpAssocOutStreams,
                 sctpAssocMaxRetr,
                 sctpAssocPrimProcess,
                 sctpAssocStartTime,
                 sctpAssocDiscontinuityTime,





                 sctpAssocLocalAddrStartTime,
                 sctpAssocRemAddrActive,
                 sctpAssocRemAddrHBActive,
                 sctpAssocRemAddrRTO,
                 sctpAssocRemAddrMaxPathRtx,
                 sctpAssocRemAddrStartTime
               }

     STATUS    current

     ::= { sctpMibGroups 3 }

   sctpPerAssocStatsGroup OBJECT-GROUP
                 OBJECTS
               { sctpAssocT1expireds,
                 sctpAssocT2expireds,
                 sctpAssocRtxChunks,
                 sctpAssocRemAddrRtx
               }

     STATUS    current

     ::= { sctpMibGroups 4 }

   sctpInverseGroup OBJECT-GROUP
     OBJECTS   { sctpLookupLocalPortStartTime,
                sctpLookupRemPortStartTime,
                sctpLookupRemHostNameStartTime,
                sctpLookupRemPrimIPAddrStartTime,
                sctpLookupRemIPAddrStartTime
               }

     STATUS    current

     ::= { sctpMibGroups 5 }











   sctpMibCompliance MODULE-COMPLIANCE
     STATUS  current

     MODULE  -- this module





          MANDATORY-GROUPS    {  sctpLayerParamsGroup,
                                 sctpPerAssocParamsGroup,
                                 sctpStatsGroup,
                                 sctpPerAssocStatsGroup
                              }

          OBJECT  sctpAssocRemPrimAddrType
          SYNTAX  InetAddressType { ipv4(1),
                                    ipv6(2)
                                  }

          OBJECT  sctpAssocRemPrimAddr
          SYNTAX  InetAddress (SIZE(4|16))


          OBJECT sctpAssocState
          WRITE-SYNTAX  INTEGER { deleteTCB(9) }
          MIN-ACCESS read-only

          GROUP sctpInverseGroup

     ::= { sctpMibCompliances 1 }

   END
