PARALLEL-MIB DEFINITIONS ::= BEGIN

   IMPORTS
       MODULE-IDENTITY, OBJECT-TYPE, NOTIFICATION-TYPE,
       Counter32, Integer32
           FROM SNMPv2-SMI
       InterfaceIndex
           FROM IF-MIB
       transmission
           FROM RFC1213-MIB
       MODULE-COMPLIANCE, OBJECT-GROUP
           FROM SNMPv2-CONF;


   para MODULE-IDENTITY
        LAST-UPDATED "9405261700Z"
        ORGANIZATION "IETF Character MIB Working Group"





       ::= { transmission 34 }



   paraNumber OBJECT-TYPE
       SYNTAX Integer32
       MAX-ACCESS read-only
       STATUS current
       ::= { para 1 }



   paraPortTable OBJECT-TYPE
       SYNTAX SEQUENCE OF ParaPortEntry
       MAX-ACCESS not-accessible
       STATUS current
       ::= { para 2 }

   paraPortEntry OBJECT-TYPE
       SYNTAX ParaPortEntry
       MAX-ACCESS not-accessible
       STATUS current
       INDEX { paraPortIndex }
       ::= { paraPortTable 1 }

   ParaPortEntry ::=
       SEQUENCE {
           paraPortIndex
               InterfaceIndex,
           paraPortType
               INTEGER,
           paraPortInSigNumber
               Integer32,
           paraPortOutSigNumber
               Integer32
       }





   paraPortIndex OBJECT-TYPE
       SYNTAX InterfaceIndex
       MAX-ACCESS read-only
       STATUS current
       ::= { paraPortEntry 1 }

   paraPortType OBJECT-TYPE
       SYNTAX INTEGER {
           other(1),
           centronics(2),
           dataproducts(3)
       }
       MAX-ACCESS read-only
       STATUS current
       ::= { paraPortEntry 2 }

   paraPortInSigNumber OBJECT-TYPE
       SYNTAX Integer32
       MAX-ACCESS read-only
       STATUS current
       ::= { paraPortEntry 3 }

   paraPortOutSigNumber OBJECT-TYPE
       SYNTAX Integer32
       MAX-ACCESS read-only
       STATUS current
       ::= { paraPortEntry 4 }









   paraInSigTable OBJECT-TYPE
       SYNTAX SEQUENCE OF ParaInSigEntry
       MAX-ACCESS not-accessible
       STATUS current
       ::= { para 3 }

   paraInSigEntry OBJECT-TYPE
       SYNTAX ParaInSigEntry
       MAX-ACCESS not-accessible
       STATUS current
       INDEX { paraInSigPortIndex, paraInSigName }
       ::= { paraInSigTable 1 }

   ParaInSigEntry ::=
       SEQUENCE {
           paraInSigPortIndex
               InterfaceIndex,
           paraInSigName
               INTEGER,
           paraInSigState
               INTEGER,
           paraInSigChanges
               Counter32
       }

   paraInSigPortIndex OBJECT-TYPE
       SYNTAX InterfaceIndex
       MAX-ACCESS read-only
       STATUS current
       ::= { paraInSigEntry 1 }

   paraInSigName OBJECT-TYPE
       SYNTAX INTEGER { power(1), online(2), busy(3),
                        paperout(4), fault(5) }
       MAX-ACCESS read-only
       STATUS current
       ::= { paraInSigEntry 2 }





   paraInSigState OBJECT-TYPE
       SYNTAX INTEGER { none(1), on(2), off(3) }
       MAX-ACCESS read-only
       STATUS current
       ::= { paraInSigEntry 3 }

   paraInSigChanges OBJECT-TYPE
       SYNTAX Counter32
       MAX-ACCESS read-only
       STATUS current
       ::= { paraInSigEntry 4 }



   paraOutSigTable OBJECT-TYPE
       SYNTAX SEQUENCE OF ParaOutSigEntry
       MAX-ACCESS not-accessible
       STATUS current
       ::= { para 4 }

   paraOutSigEntry OBJECT-TYPE
       SYNTAX ParaOutSigEntry
       MAX-ACCESS not-accessible
       STATUS current
       INDEX { paraOutSigPortIndex, paraOutSigName }
       ::= { paraOutSigTable 1 }

   ParaOutSigEntry ::=
       SEQUENCE {
           paraOutSigPortIndex
               InterfaceIndex,
           paraOutSigName
               INTEGER,
           paraOutSigState
               INTEGER,
           paraOutSigChanges
               Counter32
       }





   paraOutSigPortIndex OBJECT-TYPE
       SYNTAX InterfaceIndex
       MAX-ACCESS read-only
       STATUS current
       ::= { paraOutSigEntry 1 }

   paraOutSigName OBJECT-TYPE
       SYNTAX INTEGER { power(1), online(2), busy(3),
                        paperout(4), fault(5) }
       MAX-ACCESS read-only
       STATUS current
       ::= { paraOutSigEntry 2 }

   paraOutSigState OBJECT-TYPE
       SYNTAX INTEGER { none(1), on(2), off(3) }
       MAX-ACCESS read-only
       STATUS current
       ::= { paraOutSigEntry 3 }

   paraOutSigChanges OBJECT-TYPE
       SYNTAX Counter32
       MAX-ACCESS read-only
       STATUS current
       ::= { paraOutSigEntry 4 }



   paraConformance OBJECT IDENTIFIER ::= { para 5 }

   paraGroups      OBJECT IDENTIFIER ::= { paraConformance 1 }
   paraCompliances OBJECT IDENTIFIER ::= { paraConformance 2 }












   paraCompliance MODULE-COMPLIANCE
       STATUS  current

       MODULE  -- this module
           MANDATORY-GROUPS { paraGroup }
       ::= { paraCompliances 1 }



   paraGroup    OBJECT-GROUP
       OBJECTS { paraNumber, paraPortIndex, paraPortType,
                 paraPortInSigNumber, paraPortOutSigNumber,
                 paraInSigPortIndex, paraInSigName,
                 paraInSigState, paraInSigChanges,
                 paraOutSigPortIndex, paraOutSigName,
                 paraOutSigState, paraOutSigChanges }
       STATUS  current
       ::= { paraGroups 1 }

   END
