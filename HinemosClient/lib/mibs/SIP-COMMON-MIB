SIP-COMMON-MIB DEFINITIONS ::= BEGIN

IMPORTS
    MODULE-IDENTITY,
    OBJECT-TYPE,
    NOTIFICATION-TYPE,
    Counter32,
    Gauge32,
    TimeTicks,
    Unsigned32,





    mib-2
          FROM SNMPv2-SMI             -- RFC 2578

    RowStatus,
    TimeStamp,
    TruthValue
          FROM SNMPv2-TC              -- RFC 2579

    MODULE-COMPLIANCE,
    OBJECT-GROUP,
    NOTIFICATION-GROUP
          FROM SNMPv2-CONF            -- RFC 2580

    SnmpAdminString
          FROM SNMP-FRAMEWORK-MIB     -- RFC 3411

    SipTCTransportProtocol,
    SipTCMethodName,
    SipTCEntityRole,
    SipTCOptionTagHeaders
          FROM SIP-TC-MIB             -- RFC 4780

    applIndex
          FROM NETWORK-SERVICES-MIB   -- RFC 2788

    InetPortNumber
          FROM INET-ADDRESS-MIB;      -- RFC 4001

sipCommonMIB MODULE-IDENTITY
    LAST-UPDATED "200704200000Z"
    ORGANIZATION "IETF Session Initiation Protocol Working Group"
     ::= { mib-2 149 }

sipCommonMIBNotifications OBJECT IDENTIFIER ::= { sipCommonMIB 0 }
sipCommonMIBObjects       OBJECT IDENTIFIER ::= { sipCommonMIB 1 }
sipCommonMIBConformance   OBJECT IDENTIFIER ::= { sipCommonMIB 2 }


sipCommonCfgBase       OBJECT IDENTIFIER ::= { sipCommonMIBObjects 1 }

sipCommonCfgTimer      OBJECT IDENTIFIER ::= { sipCommonMIBObjects 2 }






sipCommonSummaryStats  OBJECT IDENTIFIER ::= { sipCommonMIBObjects 3 }

sipCommonMethodStats   OBJECT IDENTIFIER ::= { sipCommonMIBObjects 4 }

sipCommonStatusCode    OBJECT IDENTIFIER ::= { sipCommonMIBObjects 5 }

sipCommonStatsTrans    OBJECT IDENTIFIER ::= { sipCommonMIBObjects 6 }

sipCommonStatsRetry    OBJECT IDENTIFIER ::= { sipCommonMIBObjects 7 }

sipCommonOtherStats    OBJECT IDENTIFIER ::= { sipCommonMIBObjects 8 }

sipCommonNotifObjects  OBJECT IDENTIFIER ::= { sipCommonMIBObjects 9 }

sipCommonCfgTable OBJECT-TYPE
    SYNTAX      SEQUENCE OF SipCommonCfgEntry
    MAX-ACCESS  not-accessible
    STATUS      current
    ::= { sipCommonCfgBase 1 }

sipCommonCfgEntry OBJECT-TYPE
    SYNTAX      SipCommonCfgEntry
    MAX-ACCESS  not-accessible
    STATUS      current
    INDEX { applIndex }
    ::= { sipCommonCfgTable 1 }

SipCommonCfgEntry ::= SEQUENCE {





        sipCommonCfgProtocolVersion      SnmpAdminString,
        sipCommonCfgServiceOperStatus    INTEGER,
        sipCommonCfgServiceStartTime     TimeTicks,
        sipCommonCfgServiceLastChange    TimeTicks,
        sipCommonCfgOrganization         SnmpAdminString,
        sipCommonCfgMaxTransactions      Unsigned32,
        sipCommonCfgServiceNotifEnable   BITS,
        sipCommonCfgEntityType           SipTCEntityRole
    }

sipCommonCfgProtocolVersion OBJECT-TYPE
    SYNTAX      SnmpAdminString
    MAX-ACCESS  read-only
    STATUS      current
    ::= { sipCommonCfgEntry 1 }

sipCommonCfgServiceOperStatus OBJECT-TYPE
    SYNTAX      INTEGER {
                  unknown(1),
                  up(2),
                  down(3),
                  congested(4),
                  restarting(5),
                  quiescing(6),
                  testing(7)
                }
    MAX-ACCESS  read-only
    STATUS      current
    ::= { sipCommonCfgEntry 2 }

sipCommonCfgServiceStartTime OBJECT-TYPE
    SYNTAX      TimeTicks
    MAX-ACCESS  read-only
    STATUS      current
    ::= { sipCommonCfgEntry 3 }

sipCommonCfgServiceLastChange OBJECT-TYPE
    SYNTAX      TimeTicks
    MAX-ACCESS  read-only
    STATUS      current
    ::= { sipCommonCfgEntry 4 }

sipCommonCfgOrganization OBJECT-TYPE
    SYNTAX      SnmpAdminString
    MAX-ACCESS  read-only
    STATUS      current





    ::= { sipCommonCfgEntry 5 }

sipCommonCfgMaxTransactions OBJECT-TYPE
    SYNTAX      Unsigned32 (1..4294967295)
    MAX-ACCESS  read-only
    STATUS      current
    ::= { sipCommonCfgEntry 6 }

sipCommonCfgServiceNotifEnable OBJECT-TYPE
    SYNTAX      BITS {
                  sipCommonServiceColdStart(0),
                  sipCommonServiceWarmStart(1),
                  sipCommonServiceStatusChanged(2)
                }
    MAX-ACCESS  read-write
    STATUS      current
    DEFVAL { { sipCommonServiceColdStart,
               sipCommonServiceWarmStart } }
    ::= { sipCommonCfgEntry 7 }

sipCommonCfgEntityType OBJECT-TYPE
    SYNTAX      SipTCEntityRole
    MAX-ACCESS  read-only





    STATUS      current
    ::= { sipCommonCfgEntry 8 }

sipCommonPortTable OBJECT-TYPE
    SYNTAX      SEQUENCE OF SipCommonPortEntry
    MAX-ACCESS  not-accessible
    STATUS      current
    ::= { sipCommonCfgBase 2 }

sipCommonPortEntry OBJECT-TYPE
    SYNTAX      SipCommonPortEntry
    MAX-ACCESS  not-accessible
    STATUS      current
    INDEX { applIndex, sipCommonPort }
    ::= { sipCommonPortTable 1 }

SipCommonPortEntry ::= SEQUENCE {
        sipCommonPort                 InetPortNumber,
        sipCommonPortTransportRcv     SipTCTransportProtocol
    }

sipCommonPort OBJECT-TYPE
    SYNTAX      InetPortNumber (1..65535)
    MAX-ACCESS  not-accessible
    STATUS      current





    ::= { sipCommonPortEntry 1 }

sipCommonPortTransportRcv OBJECT-TYPE
    SYNTAX      SipTCTransportProtocol
    MAX-ACCESS  read-only
    STATUS      current
    ::= { sipCommonPortEntry 2 }


sipCommonOptionTagTable OBJECT-TYPE
    SYNTAX      SEQUENCE OF SipCommonOptionTagEntry
    MAX-ACCESS  not-accessible
    STATUS      current





    ::= { sipCommonCfgBase 3 }

sipCommonOptionTagEntry OBJECT-TYPE
    SYNTAX      SipCommonOptionTagEntry
    MAX-ACCESS  not-accessible
    STATUS      current
    INDEX { applIndex, sipCommonOptionTagIndex }
    ::= { sipCommonOptionTagTable 1 }

SipCommonOptionTagEntry ::= SEQUENCE {
        sipCommonOptionTagIndex        Unsigned32,
        sipCommonOptionTag             SnmpAdminString,
        sipCommonOptionTagHeaderField  SipTCOptionTagHeaders
    }

sipCommonOptionTagIndex OBJECT-TYPE
    SYNTAX      Unsigned32 (1..4294967295)
    MAX-ACCESS  not-accessible
    STATUS      current
    ::= { sipCommonOptionTagEntry 1 }

sipCommonOptionTag OBJECT-TYPE
    SYNTAX      SnmpAdminString
    MAX-ACCESS  read-only
    STATUS      current
    ::= { sipCommonOptionTagEntry 2 }

sipCommonOptionTagHeaderField OBJECT-TYPE
    SYNTAX      SipTCOptionTagHeaders
    MAX-ACCESS  read-only
    STATUS      current





    ::= { sipCommonOptionTagEntry 3 }

sipCommonMethodSupportedTable OBJECT-TYPE
    SYNTAX      SEQUENCE OF SipCommonMethodSupportedEntry
    MAX-ACCESS  not-accessible
    STATUS      current
 ::= { sipCommonCfgBase 4 }

sipCommonMethodSupportedEntry OBJECT-TYPE
    SYNTAX      SipCommonMethodSupportedEntry
    MAX-ACCESS  not-accessible
    STATUS      current
    INDEX { applIndex, sipCommonMethodSupportedIndex }
    ::= { sipCommonMethodSupportedTable 1 }

SipCommonMethodSupportedEntry ::= SEQUENCE {
        sipCommonMethodSupportedIndex     Unsigned32,
        sipCommonMethodSupportedName      SipTCMethodName
    }





sipCommonMethodSupportedIndex OBJECT-TYPE
    SYNTAX      Unsigned32 (1..4294967295)
    MAX-ACCESS  not-accessible
    STATUS      current
    ::= { sipCommonMethodSupportedEntry 1 }

sipCommonMethodSupportedName OBJECT-TYPE
    SYNTAX      SipTCMethodName
    MAX-ACCESS  read-only
    STATUS      current
 ::= { sipCommonMethodSupportedEntry 2 }

sipCommonCfgTimerTable OBJECT-TYPE
    SYNTAX      SEQUENCE OF SipCommonCfgTimerEntry
    MAX-ACCESS  not-accessible
    STATUS      current
    ::= { sipCommonCfgTimer 1 }

sipCommonCfgTimerEntry OBJECT-TYPE
    SYNTAX      SipCommonCfgTimerEntry
    MAX-ACCESS  not-accessible
    STATUS      current





    INDEX { applIndex }
    ::= { sipCommonCfgTimerTable 1 }

SipCommonCfgTimerEntry ::= SEQUENCE {
        sipCommonCfgTimerA               Unsigned32,
        sipCommonCfgTimerB               Unsigned32,
        sipCommonCfgTimerC               Unsigned32,
        sipCommonCfgTimerD               Unsigned32,
        sipCommonCfgTimerE               Unsigned32,
        sipCommonCfgTimerF               Unsigned32,
        sipCommonCfgTimerG               Unsigned32,
        sipCommonCfgTimerH               Unsigned32,
        sipCommonCfgTimerI               Unsigned32,
        sipCommonCfgTimerJ               Unsigned32,
        sipCommonCfgTimerK               Unsigned32,
        sipCommonCfgTimerT1              Unsigned32,
        sipCommonCfgTimerT2              Unsigned32,
        sipCommonCfgTimerT4              Unsigned32
    }

sipCommonCfgTimerA OBJECT-TYPE
    SYNTAX      Unsigned32 (100..1000)
    UNITS      "milliseconds"
    MAX-ACCESS  read-only
    STATUS      current
    DEFVAL { 500 }
    ::= { sipCommonCfgTimerEntry 1 }

sipCommonCfgTimerB OBJECT-TYPE
    SYNTAX      Unsigned32 (32000..300000)
    UNITS      "milliseconds"
    MAX-ACCESS  read-only
    STATUS      current





    DEFVAL { 32000 }
::= { sipCommonCfgTimerEntry 2 }

sipCommonCfgTimerC OBJECT-TYPE
    SYNTAX      Unsigned32 (180000..300000)
    UNITS      "milliseconds"
    MAX-ACCESS  read-only
    STATUS      current
    DEFVAL { 180000 }
    ::= { sipCommonCfgTimerEntry 3 }

sipCommonCfgTimerD OBJECT-TYPE
    SYNTAX      Unsigned32 (0..300000)
    UNITS      "milliseconds"
    MAX-ACCESS  read-only
    STATUS      current
    DEFVAL { 32000 }
    ::= { sipCommonCfgTimerEntry 4 }

sipCommonCfgTimerE OBJECT-TYPE
    SYNTAX      Unsigned32 (100..1000)
    UNITS      "milliseconds"
    MAX-ACCESS  read-only
    STATUS      current
    DEFVAL { 500 }
    ::= { sipCommonCfgTimerEntry 5 }

sipCommonCfgTimerF  OBJECT-TYPE
    SYNTAX      Unsigned32 (32000..300000)
    UNITS      "milliseconds"
    MAX-ACCESS  read-only
    STATUS      current
    DEFVAL { 32000 }

    ::= { sipCommonCfgTimerEntry 6 }

sipCommonCfgTimerG  OBJECT-TYPE
    SYNTAX      Unsigned32 (0..1000)
    UNITS      "milliseconds"
    MAX-ACCESS  read-only
    STATUS      current
    DEFVAL { 500 }
    ::= { sipCommonCfgTimerEntry 7 }

sipCommonCfgTimerH  OBJECT-TYPE
    SYNTAX      Unsigned32 (32000..300000)
    UNITS      "milliseconds"
    MAX-ACCESS  read-only
    STATUS      current
    DEFVAL { 32000 }
    ::= { sipCommonCfgTimerEntry 8 }

sipCommonCfgTimerI  OBJECT-TYPE
    SYNTAX      Unsigned32 (0..10000)
    UNITS      "milliseconds"
    MAX-ACCESS  read-only
    STATUS      current
    DEFVAL { 5000 }
    ::= { sipCommonCfgTimerEntry 9 }

sipCommonCfgTimerJ  OBJECT-TYPE
    SYNTAX      Unsigned32 (32000..300000)
    UNITS      "milliseconds"
    MAX-ACCESS  read-only
    STATUS      current
    DEFVAL { 32000 }
    ::= { sipCommonCfgTimerEntry 10 }

sipCommonCfgTimerK  OBJECT-TYPE
    SYNTAX      Unsigned32 (0..10000)
    UNITS      "milliseconds"
    MAX-ACCESS  read-only
    STATUS      current
    DEFVAL { 5000 }
    ::= { sipCommonCfgTimerEntry 11 }

sipCommonCfgTimerT1  OBJECT-TYPE
    SYNTAX      Unsigned32 (200..10000)
    UNITS      "milliseconds"
    MAX-ACCESS  read-only
    STATUS      current
    DEFVAL { 500 }
    ::= { sipCommonCfgTimerEntry 12 }

sipCommonCfgTimerT2  OBJECT-TYPE
    SYNTAX      Unsigned32 (200..10000)
    UNITS      "milliseconds"
    MAX-ACCESS  read-only
    STATUS      current
    DEFVAL { 4000 }
    ::= { sipCommonCfgTimerEntry 13 }

sipCommonCfgTimerT4  OBJECT-TYPE
    SYNTAX      Unsigned32 (200..10000)
    UNITS      "milliseconds"
    MAX-ACCESS  read-only
    STATUS      current
    DEFVAL { 5000 }
    ::= { sipCommonCfgTimerEntry 14 }


sipCommonSummaryStatsTable OBJECT-TYPE
    SYNTAX      SEQUENCE OF SipCommonSummaryStatsEntry
    MAX-ACCESS  not-accessible
    STATUS      current
    ::= { sipCommonSummaryStats 1 }

sipCommonSummaryStatsEntry OBJECT-TYPE
    SYNTAX      SipCommonSummaryStatsEntry
    MAX-ACCESS  not-accessible
    STATUS      current
    INDEX { applIndex }
    ::= { sipCommonSummaryStatsTable 1 }

SipCommonSummaryStatsEntry ::= SEQUENCE {
        sipCommonSummaryInRequests         Counter32,
        sipCommonSummaryOutRequests        Counter32,
        sipCommonSummaryInResponses        Counter32,
        sipCommonSummaryOutResponses       Counter32,
        sipCommonSummaryTotalTransactions  Counter32,
        sipCommonSummaryDisconTime         TimeStamp
    }

sipCommonSummaryInRequests OBJECT-TYPE





    SYNTAX      Counter32
    MAX-ACCESS  read-only
    STATUS      current
    ::= { sipCommonSummaryStatsEntry 1 }

sipCommonSummaryOutRequests OBJECT-TYPE
    SYNTAX      Counter32
    MAX-ACCESS  read-only
    STATUS      current
    ::= { sipCommonSummaryStatsEntry 2 }

sipCommonSummaryInResponses OBJECT-TYPE
    SYNTAX      Counter32
    MAX-ACCESS  read-only
    STATUS      current
    ::= { sipCommonSummaryStatsEntry 3 }

sipCommonSummaryOutResponses OBJECT-TYPE





    SYNTAX      Counter32
    MAX-ACCESS  read-only
    STATUS      current
    ::= { sipCommonSummaryStatsEntry 4 }

sipCommonSummaryTotalTransactions OBJECT-TYPE
    SYNTAX      Counter32
    MAX-ACCESS  read-only
    STATUS      current
    ::= { sipCommonSummaryStatsEntry 5 }

sipCommonSummaryDisconTime  OBJECT-TYPE
    SYNTAX      TimeStamp
    MAX-ACCESS  read-only
    STATUS      current
    ::= { sipCommonSummaryStatsEntry 6 }

sipCommonMethodStatsTable OBJECT-TYPE
    SYNTAX      SEQUENCE OF SipCommonMethodStatsEntry
    MAX-ACCESS  not-accessible
    STATUS      current
    ::= { sipCommonMethodStats 1 }

sipCommonMethodStatsEntry OBJECT-TYPE
    SYNTAX      SipCommonMethodStatsEntry
    MAX-ACCESS  not-accessible
    STATUS      current
    INDEX { applIndex, sipCommonMethodStatsName }
    ::= { sipCommonMethodStatsTable 1 }

SipCommonMethodStatsEntry ::= SEQUENCE {
        sipCommonMethodStatsName   SipTCMethodName,
        sipCommonMethodStatsOutbounds    Counter32,





        sipCommonMethodStatsInbounds     Counter32,
        sipCommonMethodStatsDisconTime   TimeStamp

    }

sipCommonMethodStatsName OBJECT-TYPE
    SYNTAX      SipTCMethodName
    MAX-ACCESS  not-accessible
    STATUS      current
    ::= { sipCommonMethodStatsEntry 1 }

sipCommonMethodStatsOutbounds OBJECT-TYPE
    SYNTAX      Counter32
    MAX-ACCESS  read-only
    STATUS      current
    ::= { sipCommonMethodStatsEntry 2 }

sipCommonMethodStatsInbounds OBJECT-TYPE
    SYNTAX      Counter32
    MAX-ACCESS  read-only
    STATUS      current
    ::= { sipCommonMethodStatsEntry 3 }

sipCommonMethodStatsDisconTime  OBJECT-TYPE
    SYNTAX      TimeStamp
    MAX-ACCESS  read-only
    STATUS      current
    ::= { sipCommonMethodStatsEntry 4 }

sipCommonStatusCodeTable OBJECT-TYPE
    SYNTAX      SEQUENCE OF SipCommonStatusCodeEntry
    MAX-ACCESS  not-accessible
    STATUS      current
    ::= { sipCommonStatusCode 1 }

sipCommonStatusCodeEntry OBJECT-TYPE
    SYNTAX      SipCommonStatusCodeEntry
    MAX-ACCESS  not-accessible
    STATUS      current
    INDEX { applIndex, sipCommonStatusCodeMethod,
            sipCommonStatusCodeValue }
    ::= { sipCommonStatusCodeTable 1 }

SipCommonStatusCodeEntry ::= SEQUENCE {
        sipCommonStatusCodeMethod     SipTCMethodName,
        sipCommonStatusCodeValue      Unsigned32,
        sipCommonStatusCodeIns        Counter32,
        sipCommonStatusCodeOuts       Counter32,
        sipCommonStatusCodeRowStatus  RowStatus,
        sipCommonStatusCodeDisconTime TimeStamp
    }

sipCommonStatusCodeMethod OBJECT-TYPE
    SYNTAX      SipTCMethodName
    MAX-ACCESS  not-accessible





    STATUS      current
    ::= { sipCommonStatusCodeEntry 1 }

sipCommonStatusCodeValue OBJECT-TYPE
    SYNTAX      Unsigned32 (100..999)
    MAX-ACCESS  not-accessible
    STATUS      current
    ::= { sipCommonStatusCodeEntry 2 }

sipCommonStatusCodeIns OBJECT-TYPE
    SYNTAX      Counter32
    MAX-ACCESS  read-only
    STATUS      current
    ::= { sipCommonStatusCodeEntry 3 }

sipCommonStatusCodeOuts OBJECT-TYPE
    SYNTAX      Counter32
    MAX-ACCESS  read-only
    STATUS      current





    ::= { sipCommonStatusCodeEntry 4 }

sipCommonStatusCodeRowStatus OBJECT-TYPE
    SYNTAX      RowStatus
    MAX-ACCESS  read-create
    STATUS      current
    ::= { sipCommonStatusCodeEntry 5 }

sipCommonStatusCodeDisconTime  OBJECT-TYPE
    SYNTAX TimeStamp
    MAX-ACCESS read-only
    STATUS current
    ::= { sipCommonStatusCodeEntry 6 }


sipCommonStatusCodeNotifTable OBJECT-TYPE
    SYNTAX      SEQUENCE OF SipCommonStatusCodeNotifEntry
    MAX-ACCESS  not-accessible
    STATUS      current
    ::= { sipCommonStatusCode 2 }





sipCommonStatusCodeNotifEntry OBJECT-TYPE
    SYNTAX      SipCommonStatusCodeNotifEntry
    MAX-ACCESS  not-accessible
    STATUS      current
    AUGMENTS { sipCommonStatusCodeEntry }
    ::= { sipCommonStatusCodeNotifTable 1 }

SipCommonStatusCodeNotifEntry ::= SEQUENCE {
        sipCommonStatusCodeNotifSend         TruthValue,
        sipCommonStatusCodeNotifEmitMode     INTEGER,
        sipCommonStatusCodeNotifThresh       Unsigned32,
        sipCommonStatusCodeNotifInterval     Unsigned32
    }

sipCommonStatusCodeNotifSend OBJECT-TYPE
    SYNTAX      TruthValue
    MAX-ACCESS  read-write
    STATUS      current
    DEFVAL { false }
    ::= { sipCommonStatusCodeNotifEntry 1 }

sipCommonStatusCodeNotifEmitMode OBJECT-TYPE
    SYNTAX      INTEGER {
                  normal(1),
                  oneShot(2),
                  triggered(3)  -- read-only
                }
    MAX-ACCESS  read-write
    STATUS      current
    DEFVAL { oneShot }
    ::= { sipCommonStatusCodeNotifEntry 2 }

sipCommonStatusCodeNotifThresh OBJECT-TYPE
    SYNTAX      Unsigned32
    MAX-ACCESS  read-write
    STATUS      current
    DEFVAL { 500 }
    ::= { sipCommonStatusCodeNotifEntry 3 }

sipCommonStatusCodeNotifInterval OBJECT-TYPE
    SYNTAX      Unsigned32
    UNITS      "seconds"
    MAX-ACCESS  read-write
    STATUS      current
    DEFVAL { 60 }
    ::= { sipCommonStatusCodeNotifEntry 4 }

sipCommonTransCurrentTable OBJECT-TYPE
    SYNTAX      SEQUENCE OF SipCommonTransCurrentEntry
    MAX-ACCESS  not-accessible
    STATUS      current
    ::= { sipCommonStatsTrans 1 }

sipCommonTransCurrentEntry OBJECT-TYPE
    SYNTAX      SipCommonTransCurrentEntry
    MAX-ACCESS  not-accessible
    STATUS      current
    INDEX { applIndex }
    ::= { sipCommonTransCurrentTable 1 }

SipCommonTransCurrentEntry ::= SEQUENCE {
        sipCommonTransCurrentactions  Gauge32
    }

sipCommonTransCurrentactions OBJECT-TYPE
    SYNTAX      Gauge32 (0..4294967295)
    MAX-ACCESS  read-only
    STATUS      current
::= { sipCommonTransCurrentEntry 1 }

sipCommonStatsRetryTable OBJECT-TYPE
    SYNTAX      SEQUENCE OF SipCommonStatsRetryEntry
    MAX-ACCESS  not-accessible
    STATUS      current
    ::= { sipCommonStatsRetry 1 }

sipCommonStatsRetryEntry OBJECT-TYPE
    SYNTAX      SipCommonStatsRetryEntry
    MAX-ACCESS  not-accessible
    STATUS      current





    INDEX { applIndex, sipCommonStatsRetryMethod }
    ::= { sipCommonStatsRetryTable 1 }

SipCommonStatsRetryEntry ::= SEQUENCE {
        sipCommonStatsRetryMethod            SipTCMethodName,
        sipCommonStatsRetries                Counter32,
        sipCommonStatsRetryFinalResponses    Counter32,
        sipCommonStatsRetryNonFinalResponses Counter32,
        sipCommonStatsRetryDisconTime        TimeStamp
    }

sipCommonStatsRetryMethod OBJECT-TYPE
    SYNTAX      SipTCMethodName
    MAX-ACCESS  not-accessible
    STATUS      current
    ::= { sipCommonStatsRetryEntry 1 }

sipCommonStatsRetries OBJECT-TYPE
    SYNTAX      Counter32
    MAX-ACCESS  read-only
    STATUS      current
    ::= { sipCommonStatsRetryEntry 2 }

sipCommonStatsRetryFinalResponses OBJECT-TYPE
    SYNTAX      Counter32
    MAX-ACCESS  read-only
    STATUS      current
    ::= { sipCommonStatsRetryEntry 3 }

sipCommonStatsRetryNonFinalResponses OBJECT-TYPE
    SYNTAX      Counter32
    MAX-ACCESS  read-only
    STATUS      current
    ::= { sipCommonStatsRetryEntry 4 }

sipCommonStatsRetryDisconTime  OBJECT-TYPE
    SYNTAX      TimeStamp
    MAX-ACCESS  read-only
    STATUS      current
    ::= { sipCommonStatsRetryEntry 5 }

sipCommonOtherStatsTable OBJECT-TYPE
    SYNTAX      SEQUENCE OF SipCommonOtherStatsEntry
    MAX-ACCESS  not-accessible
    STATUS      current
    ::= { sipCommonOtherStats 1 }

sipCommonOtherStatsEntry OBJECT-TYPE
    SYNTAX      SipCommonOtherStatsEntry
    MAX-ACCESS  not-accessible
    STATUS      current
    INDEX { applIndex }
    ::= { sipCommonOtherStatsTable 1 }

SipCommonOtherStatsEntry ::= SEQUENCE {
        sipCommonOtherStatsNumUnsupportedUris     Counter32,
        sipCommonOtherStatsNumUnsupportedMethods  Counter32,
        sipCommonOtherStatsOtherwiseDiscardedMsgs Counter32,
        sipCommonOtherStatsDisconTime   TimeStamp
    }

sipCommonOtherStatsNumUnsupportedUris OBJECT-TYPE
    SYNTAX      Counter32
    MAX-ACCESS  read-only
    STATUS      current
    ::= { sipCommonOtherStatsEntry 1 }

sipCommonOtherStatsNumUnsupportedMethods OBJECT-TYPE
    SYNTAX      Counter32
    MAX-ACCESS  read-only
    STATUS      current
    ::= { sipCommonOtherStatsEntry 2 }

sipCommonOtherStatsOtherwiseDiscardedMsgs OBJECT-TYPE
    SYNTAX      Counter32





    MAX-ACCESS  read-only
    STATUS      current
    ::= { sipCommonOtherStatsEntry 3 }

sipCommonOtherStatsDisconTime OBJECT-TYPE
    SYNTAX      TimeStamp
    MAX-ACCESS  read-only
    STATUS      current
    ::= { sipCommonOtherStatsEntry 4 }


sipCommonStatusCodeNotifTo OBJECT-TYPE
    SYNTAX      SnmpAdminString
    MAX-ACCESS  accessible-for-notify
    STATUS      current
    ::= { sipCommonNotifObjects 1 }

sipCommonStatusCodeNotifFrom OBJECT-TYPE
    SYNTAX      SnmpAdminString
    MAX-ACCESS  accessible-for-notify
    STATUS      current
    ::= { sipCommonNotifObjects 2 }

sipCommonStatusCodeNotifCallId OBJECT-TYPE
    SYNTAX      SnmpAdminString
    MAX-ACCESS  accessible-for-notify
    STATUS      current
    ::= { sipCommonNotifObjects 3 }

sipCommonStatusCodeNotifCSeq OBJECT-TYPE
    SYNTAX      Unsigned32
    MAX-ACCESS  accessible-for-notify
    STATUS      current
    ::= { sipCommonNotifObjects 4 }

sipCommonNotifApplIndex OBJECT-TYPE
    SYNTAX      Unsigned32 (1..2147483647)
    MAX-ACCESS  accessible-for-notify
    STATUS      current
    ::= { sipCommonNotifObjects 5 }

sipCommonNotifSequenceNumber OBJECT-TYPE
    SYNTAX      Unsigned32 (1..2147483647)
    MAX-ACCESS  accessible-for-notify
    STATUS      current
    ::= { sipCommonNotifObjects 6 }

sipCommonStatusCodeNotif NOTIFICATION-TYPE
    OBJECTS {
       sipCommonNotifSequenceNumber,
       sipCommonNotifApplIndex,
       sipCommonStatusCodeNotifTo,
       sipCommonStatusCodeNotifFrom,
       sipCommonStatusCodeNotifCallId,
       sipCommonStatusCodeNotifCSeq,
       sipCommonStatusCodeIns,
       sipCommonStatusCodeOuts
    }
    STATUS      current
    ::= { sipCommonMIBNotifications 1 }

sipCommonStatusCodeThreshExceededInNotif NOTIFICATION-TYPE
    OBJECTS {
       sipCommonNotifSequenceNumber,
       sipCommonNotifApplIndex,
       sipCommonStatusCodeIns
    }
    STATUS      current
    ::= { sipCommonMIBNotifications 2 }

sipCommonStatusCodeThreshExceededOutNotif NOTIFICATION-TYPE
    OBJECTS {
       sipCommonNotifSequenceNumber,
       sipCommonNotifApplIndex,
       sipCommonStatusCodeOuts
    }
    STATUS      current





    ::= { sipCommonMIBNotifications 3 }

sipCommonServiceColdStart NOTIFICATION-TYPE
    OBJECTS {
       sipCommonNotifSequenceNumber,
       sipCommonNotifApplIndex,
       sipCommonCfgServiceStartTime
    }
    STATUS      current
    ::= { sipCommonMIBNotifications 4 }

sipCommonServiceWarmStart NOTIFICATION-TYPE
    OBJECTS {
       sipCommonNotifSequenceNumber,
       sipCommonNotifApplIndex,
       sipCommonCfgServiceLastChange
    }
    STATUS      current
    ::= { sipCommonMIBNotifications 5 }

sipCommonServiceStatusChanged NOTIFICATION-TYPE
    OBJECTS {
       sipCommonNotifSequenceNumber,
       sipCommonNotifApplIndex,
       sipCommonCfgServiceLastChange,
       sipCommonCfgServiceOperStatus
    }
    STATUS      current
    ::= { sipCommonMIBNotifications 6 }






sipCommonMIBCompliances
    OBJECT IDENTIFIER ::= { sipCommonMIBConformance 1 }
sipCommonMIBGroups
    OBJECT IDENTIFIER ::= { sipCommonMIBConformance 2 }

sipCommonCompliance MODULE-COMPLIANCE
    STATUS      current

    MODULE -- this module
        MANDATORY-GROUPS { sipCommonConfigGroup,
                           sipCommonStatsGroup
                         }

    OBJECT       sipCommonStatusCodeRowStatus
    SYNTAX       RowStatus { active(1) }
    WRITE-SYNTAX RowStatus { createAndGo(4), destroy(6) }

    OBJECT       sipCommonCfgServiceNotifEnable
    MIN-ACCESS   not-accessible

    GROUP        sipCommonInformationalGroup

    GROUP        sipCommonConfigTimerGroup

    GROUP        sipCommonStatsRetryGroup

    GROUP        sipCommonNotifGroup

    GROUP        sipCommonStatusCodeNotifGroup

    GROUP        sipCommonNotifObjectsGroup

    ::= { sipCommonMIBCompliances 1 }

sipCommonConfigGroup OBJECT-GROUP
    OBJECTS {
            sipCommonCfgProtocolVersion,
            sipCommonCfgServiceOperStatus,
            sipCommonCfgServiceStartTime,
            sipCommonCfgServiceLastChange,
            sipCommonPortTransportRcv,
            sipCommonOptionTag,
            sipCommonOptionTagHeaderField,
            sipCommonCfgMaxTransactions,
            sipCommonCfgServiceNotifEnable,
            sipCommonCfgEntityType,
            sipCommonMethodSupportedName
    }
    STATUS  current
    ::= { sipCommonMIBGroups 1 }

sipCommonInformationalGroup OBJECT-GROUP
    OBJECTS {
            sipCommonCfgOrganization
    }
    STATUS  current





    ::= { sipCommonMIBGroups 2 }

sipCommonConfigTimerGroup OBJECT-GROUP
    OBJECTS {
            sipCommonCfgTimerA,
            sipCommonCfgTimerB,
            sipCommonCfgTimerC,
            sipCommonCfgTimerD,
            sipCommonCfgTimerE,
            sipCommonCfgTimerF,
            sipCommonCfgTimerG,
            sipCommonCfgTimerH,
            sipCommonCfgTimerI,
            sipCommonCfgTimerJ,
            sipCommonCfgTimerK,
            sipCommonCfgTimerT1,
            sipCommonCfgTimerT2,
            sipCommonCfgTimerT4
    }
    STATUS  current
    ::= { sipCommonMIBGroups 3 }

sipCommonStatsGroup OBJECT-GROUP
    OBJECTS {
            sipCommonSummaryInRequests,
            sipCommonSummaryOutRequests,
            sipCommonSummaryInResponses,
            sipCommonSummaryOutResponses,
            sipCommonSummaryTotalTransactions,
            sipCommonSummaryDisconTime,
            sipCommonMethodStatsOutbounds,
            sipCommonMethodStatsInbounds,
            sipCommonMethodStatsDisconTime,
            sipCommonStatusCodeIns,
            sipCommonStatusCodeOuts,
            sipCommonStatusCodeRowStatus,
            sipCommonStatusCodeDisconTime,
            sipCommonTransCurrentactions,
            sipCommonOtherStatsNumUnsupportedUris,
            sipCommonOtherStatsNumUnsupportedMethods,
            sipCommonOtherStatsOtherwiseDiscardedMsgs,
            sipCommonOtherStatsDisconTime





    }
    STATUS  current
    ::= { sipCommonMIBGroups 4 }

sipCommonStatsRetryGroup OBJECT-GROUP
    OBJECTS {
             sipCommonStatsRetries,
             sipCommonStatsRetryFinalResponses,
             sipCommonStatsRetryNonFinalResponses,
             sipCommonStatsRetryDisconTime
    }
    STATUS  current
    ::= { sipCommonMIBGroups 5 }

sipCommonNotifGroup NOTIFICATION-GROUP
    NOTIFICATIONS {
            sipCommonStatusCodeNotif,
            sipCommonStatusCodeThreshExceededInNotif,
            sipCommonStatusCodeThreshExceededOutNotif,
            sipCommonServiceColdStart,
            sipCommonServiceWarmStart,
            sipCommonServiceStatusChanged
    }

    STATUS  current
    ::= { sipCommonMIBGroups 6 }

sipCommonStatusCodeNotifGroup OBJECT-GROUP
    OBJECTS {
            sipCommonStatusCodeNotifSend,
            sipCommonStatusCodeNotifEmitMode,
            sipCommonStatusCodeNotifThresh,
            sipCommonStatusCodeNotifInterval
   }
    STATUS  current
    ::= { sipCommonMIBGroups 7 }

sipCommonNotifObjectsGroup OBJECT-GROUP





    OBJECTS {
            sipCommonStatusCodeNotifTo,
            sipCommonStatusCodeNotifFrom,
            sipCommonStatusCodeNotifCallId,
            sipCommonStatusCodeNotifCSeq,
            sipCommonNotifApplIndex,
            sipCommonNotifSequenceNumber
    }
    STATUS  current
    ::= { sipCommonMIBGroups 8 }

END
