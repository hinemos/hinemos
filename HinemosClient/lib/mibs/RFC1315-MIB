RFC1315-MIB DEFINITIONS ::= BEGIN

     IMPORTS
             OBJECT-TYPE
                     FROM RFC-1212
             transmission
                     FROM RFC1213-MIB
             TimeTicks
                     FROM RFC1155-SMI
             TRAP-TYPE
                     FROM RFC-1215;


     frame-relay     OBJECT IDENTIFIER ::= { transmission 32 }

     Index ::= INTEGER       -- 1..ifNumber

     DLCI ::= INTEGER        -- 0..DLCINumber




     frDlcmiTable OBJECT-TYPE
         SYNTAX   SEQUENCE OF FrDlcmiEntry
         ACCESS   not-accessible
         STATUS   mandatory
         ::= { frame-relay 1 }

         frDlcmiEntry OBJECT-TYPE
             SYNTAX   FrDlcmiEntry
             ACCESS   not-accessible
             STATUS   mandatory
            INDEX { frDlcmiIfIndex }
            ::= { frDlcmiTable 1 }

         FrDlcmiEntry ::=
             SEQUENCE {
                 frDlcmiIfIndex
                     Index,
                 frDlcmiState
                     INTEGER,
                 frDlcmiAddress
                     INTEGER,
                 frDlcmiAddressLen
                     INTEGER,
                 frDlcmiPollingInterval
                     INTEGER,
                 frDlcmiFullEnquiryInterval
                     INTEGER,
                 frDlcmiErrorThreshold
                     INTEGER,
                 frDlcmiMonitoredEvents
                     INTEGER,
                 frDlcmiMaxSupportedVCs
                     INTEGER,
                 frDlcmiMulticast
                     INTEGER
         }



         frDlcmiIfIndex OBJECT-TYPE
             SYNTAX   Index
             ACCESS   read-only
             STATUS   mandatory
            ::= { frDlcmiEntry 1 }






         frDlcmiState OBJECT-TYPE
             SYNTAX INTEGER {
                 noLmiConfigured (1),
                 lmiRev1         (2),
                 ansiT1-617-D    (3),  -- ANSI T1.617 Annex D
                 ansiT1-617-B    (4)   -- ANSI T1.617 Annex B
             }
             ACCESS   read-write
             STATUS   mandatory
           ::= { frDlcmiEntry 2 }



         frDlcmiAddress OBJECT-TYPE
             SYNTAX      INTEGER {
                         q921           (1),  -- 13 bit DLCI
                         q922March90    (2),  -- 11 bit DLCI
                         q922November90 (3),  -- 10 bit DLCI
                         q922           (4)   -- Final Standard
             }
             ACCESS  read-write
             STATUS  mandatory
            ::= { frDlcmiEntry 3 }


         frDlcmiAddressLen OBJECT-TYPE
             SYNTAX  INTEGER {
                     two-octets (2),
                     three-octets (3),
                     four-octets (4)
             }
             ACCESS  read-write
             STATUS  mandatory





            ::= { frDlcmiEntry 4 }



         frDlcmiPollingInterval OBJECT-TYPE
             SYNTAX   INTEGER (5..30)
             ACCESS   read-write
             STATUS   mandatory
           DEFVAL { 10 }
           ::= { frDlcmiEntry 5 }


         frDlcmiFullEnquiryInterval OBJECT-TYPE
             SYNTAX   INTEGER (1..255)
             ACCESS   read-write
             STATUS   mandatory
           DEFVAL { 6 }
           ::= { frDlcmiEntry 6 }



         frDlcmiErrorThreshold OBJECT-TYPE
             SYNTAX   INTEGER (1..10)
             ACCESS   read-write
             STATUS   mandatory
           DEFVAL { 3 }
           ::= { frDlcmiEntry 7 }






         frDlcmiMonitoredEvents OBJECT-TYPE
             SYNTAX   INTEGER (1..10)
             ACCESS   read-write
             STATUS   mandatory
           DEFVAL { 4 }
           ::= { frDlcmiEntry 8 }



         frDlcmiMaxSupportedVCs OBJECT-TYPE
             SYNTAX   INTEGER
             ACCESS   read-write
             STATUS   mandatory
            ::= { frDlcmiEntry 9 }


         frDlcmiMulticast OBJECT-TYPE
             SYNTAX   INTEGER {
                         nonBroadcast (1),
                         broadcast (2)
                         }
             ACCESS   read-write
             STATUS   mandatory
            ::= { frDlcmiEntry 10 }










     frCircuitTable OBJECT-TYPE
         SYNTAX   SEQUENCE OF FrCircuitEntry
         ACCESS   not-accessible
         STATUS   mandatory
         ::= { frame-relay 2 }

         frCircuitEntry OBJECT-TYPE
             SYNTAX   FrCircuitEntry
             ACCESS   not-accessible
             STATUS   mandatory
            INDEX { frCircuitIfIndex, frCircuitDlci }
            ::= { frCircuitTable 1 }


         FrCircuitEntry ::=
             SEQUENCE {
                 frCircuitIfIndex
                     Index,
                 frCircuitDlci
                     DLCI,
                 frCircuitState
                     INTEGER,
                 frCircuitReceivedFECNs
                     Counter,
                 frCircuitReceivedBECNs





                     Counter,
                 frCircuitSentFrames
                     Counter,
                 frCircuitSentOctets
                     Counter,
                 frCircuitReceivedFrames
                     Counter,
                 frCircuitReceivedOctets
                     Counter,
                 frCircuitCreationTime
                     TimeTicks,
                 frCircuitLastTimeChange
                     TimeTicks,
                 frCircuitCommittedBurst
                     INTEGER,
                 frCircuitExcessBurst
                     INTEGER,
                 frCircuitThroughput
                     INTEGER
         }



         frCircuitIfIndex OBJECT-TYPE
             SYNTAX   Index
             ACCESS   read-only
             STATUS   mandatory
            ::= { frCircuitEntry 1 }


         frCircuitDlci OBJECT-TYPE
             SYNTAX   DLCI
             ACCESS   read-only
             STATUS   mandatory
           ::= { frCircuitEntry 2 }









         frCircuitState OBJECT-TYPE
             SYNTAX   INTEGER {
                         invalid (1),
                         active (2),
                         inactive (3)
                      }
             ACCESS   read-write
             STATUS   mandatory
            DEFVAL { active }
            ::= { frCircuitEntry 3 }


         frCircuitReceivedFECNs OBJECT-TYPE
             SYNTAX   Counter
             ACCESS   read-only
             STATUS   mandatory
           ::= { frCircuitEntry 4 }



         frCircuitReceivedBECNs OBJECT-TYPE
             SYNTAX   Counter
             ACCESS   read-only
             STATUS   mandatory





           ::= { frCircuitEntry 5 }



         frCircuitSentFrames OBJECT-TYPE
             SYNTAX   Counter
             ACCESS   read-only
             STATUS   mandatory
            ::= { frCircuitEntry 6 }



         frCircuitSentOctets OBJECT-TYPE
             SYNTAX   Counter
             ACCESS   read-only
             STATUS   mandatory
            ::= { frCircuitEntry 7 }



         frCircuitReceivedFrames OBJECT-TYPE
             SYNTAX   Counter
             ACCESS   read-only
             STATUS   mandatory
            ::= { frCircuitEntry 8 }



         frCircuitReceivedOctets OBJECT-TYPE
             SYNTAX   Counter
             ACCESS   read-only
             STATUS   mandatory
            ::= { frCircuitEntry 9 }





         frCircuitCreationTime OBJECT-TYPE
             SYNTAX   TimeTicks
             ACCESS   read-only
             STATUS   mandatory
            ::= { frCircuitEntry 10 }



         frCircuitLastTimeChange OBJECT-TYPE
             SYNTAX   TimeTicks
             ACCESS   read-only
             STATUS   mandatory
            ::= { frCircuitEntry 11 }



         frCircuitCommittedBurst OBJECT-TYPE
             SYNTAX   INTEGER
             ACCESS   read-write
             STATUS   mandatory
           DEFVAL   { 0 }  -- the default indicates no commitment
           ::= { frCircuitEntry 12 }



         frCircuitExcessBurst OBJECT-TYPE
             SYNTAX   INTEGER
             ACCESS   read-write
             STATUS   mandatory
                   ::= { frCircuitEntry 13 }



         frCircuitThroughput OBJECT-TYPE
             SYNTAX   INTEGER
             ACCESS   read-write
             STATUS   mandatory
           DEFVAL {0}  -- the default value of Throughput is
           ::= { frCircuitEntry 14 }




     frErrTable OBJECT-TYPE
         SYNTAX   SEQUENCE OF FrErrEntry
         ACCESS   not-accessible





         STATUS   mandatory
         ::= { frame-relay 3 }

         frErrEntry OBJECT-TYPE
             SYNTAX   FrErrEntry
             ACCESS   not-accessible
             STATUS   mandatory
            INDEX { frErrIfIndex }
            ::= { frErrTable 1 }



         FrErrEntry ::=
             SEQUENCE {
                 frErrIfIndex
                     Index,
                 frErrType
                     INTEGER,
                 frErrData
                     OCTET STRING,
                 frErrTime
                     TimeTicks
         }



         frErrIfIndex OBJECT-TYPE
             SYNTAX   Index
             ACCESS   read-only
             STATUS   mandatory
            ::= { frErrEntry 1 }



         frErrType OBJECT-TYPE
             SYNTAX   INTEGER {
                         unknownError(1),
                         receiveShort(2),
                         receiveLong(3),





                         illegalDLCI(4),
                         unknownDLCI(5),
                         dlcmiProtoErr(6),
                         dlcmiUnknownIE(7),
                         dlcmiSequenceErr(8),
                         dlcmiUnknownRpt(9),
                         noErrorSinceReset(10)
                      }
             ACCESS   read-only
             STATUS   mandatory
            ::= { frErrEntry 2 }



         frErrData OBJECT-TYPE
             SYNTAX   OCTET STRING
             ACCESS   read-only
             STATUS   mandatory
            ::= { frErrEntry 3 }



         frErrTime OBJECT-TYPE
             SYNTAX   TimeTicks
             ACCESS   read-only
             STATUS   mandatory
            ::= { frErrEntry 4 }



         frame-relay-globals OBJECT IDENTIFIER ::= { frame-relay 4 }

         frTrapState OBJECT-TYPE
             SYNTAX  INTEGER { enabled(1), disabled(2) }
             ACCESS   read-write





             STATUS   mandatory
            DEFVAL { disabled }
            ::= { frame-relay-globals 1 }



         frDLCIStatusChange TRAP-TYPE
             ENTERPRISE frame-relay
             VARIABLES  { frCircuitIfIndex, frCircuitDlci, frCircuitState }
             ::= 1

     END
