SCSI-MIB DEFINITIONS ::= BEGIN

      IMPORTS
      MODULE-IDENTITY, OBJECT-IDENTITY, OBJECT-TYPE,
      NOTIFICATION-TYPE, Integer32, Unsigned32, Counter32,
      Counter64, Gauge32,
      mib-2                                     FROM SNMPv2-SMI
      TEXTUAL-CONVENTION, TimeStamp, TruthValue,
      RowStatus, RowPointer, AutonomousType,
      StorageType                               FROM SNMPv2-TC
      MODULE-COMPLIANCE, OBJECT-GROUP,
      NOTIFICATION-GROUP                        FROM SNMPv2-CONF
      SnmpAdminString                  FROM SNMP-FRAMEWORK-MIB;

   scsiMIB MODULE-IDENTITY
        LAST-UPDATED "200603300000Z"        -- 30th March 2006
        ORGANIZATION "IETF"


   ::= { mib-2 139}

   ScsiLUN  ::= TEXTUAL-CONVENTION





        STATUS current
        SYNTAX OCTET STRING (SIZE ( 2 | 8))

   ScsiIndexValue ::= TEXTUAL-CONVENTION
        DISPLAY-HINT "d"
        STATUS current
        SYNTAX Unsigned32 (1..4294967295)

   ScsiPortIndexValueOrZero ::= TEXTUAL-CONVENTION
        DISPLAY-HINT "d"
        STATUS current
        SYNTAX Unsigned32 (0..4294967295)

   ScsiIndexValueOrZero ::= TEXTUAL-CONVENTION
        DISPLAY-HINT "d"
        STATUS current
        SYNTAX Unsigned32 (0..4294967295)

   ScsiIdentifier ::= TEXTUAL-CONVENTION





        STATUS current
        SYNTAX OCTET STRING (SIZE (0..262))

   ScsiName ::= TEXTUAL-CONVENTION
        STATUS current
        SYNTAX OCTET STRING (SIZE (0..262))

   ScsiLuNameOrZero  ::= TEXTUAL-CONVENTION
        STATUS current
        SYNTAX OCTET STRING (SIZE (0 | 8))



   ScsiDeviceOrPort ::= TEXTUAL-CONVENTION





        STATUS current
        SYNTAX INTEGER  {
            device(1),
            port(2),
            other(3)
         }

   ScsiIdCodeSet ::= TEXTUAL-CONVENTION
        DISPLAY-HINT "d"
        STATUS current
        SYNTAX Unsigned32 (0..15)

   ScsiIdAssociation ::= TEXTUAL-CONVENTION
        DISPLAY-HINT "d"
        STATUS current
        SYNTAX Unsigned32 (0..3)

   ScsiIdType ::= TEXTUAL-CONVENTION
        DISPLAY-HINT "d"
        STATUS current
        SYNTAX Unsigned32 (0..15)

   ScsiIdValue ::= TEXTUAL-CONVENTION
        STATUS current
        SYNTAX OCTET STRING (SIZE (0..255))

   ScsiHrSWInstalledIndexOrZero ::= TEXTUAL-CONVENTION
        DISPLAY-HINT "d"
        STATUS current
        SYNTAX   Integer32 (0..2147483647)


   scsiNotifications OBJECT IDENTIFIER ::= { scsiMIB 0 }
   scsiAdmin         OBJECT IDENTIFIER ::= { scsiMIB 1 }
   scsiObjects       OBJECT IDENTIFIER ::= { scsiMIB 2 }
   scsiConformance   OBJECT IDENTIFIER ::= { scsiMIB 3 }

   scsiTransportTypes   OBJECT IDENTIFIER ::= { scsiAdmin 1 }
   scsiGeneral          OBJECT IDENTIFIER ::= { scsiObjects 1 }
   scsiInitiatorDevice  OBJECT IDENTIFIER ::= { scsiObjects 2 }
   scsiTargetDevice     OBJECT IDENTIFIER ::= { scsiObjects 3 }





   scsiLogicalUnit      OBJECT IDENTIFIER ::= { scsiObjects 4 }


   scsiTransportOther   OBJECT-IDENTITY
      STATUS   current
   ::= { scsiTransportTypes 1 }

   scsiTransportSPI     OBJECT-IDENTITY
      STATUS   current
   ::= { scsiTransportTypes 2 }

   scsiTransportFCP     OBJECT-IDENTITY
      STATUS   current
   ::= { scsiTransportTypes 3 }

   scsiTransportSRP  OBJECT-IDENTITY
      STATUS   current
   ::= { scsiTransportTypes 4 }

   scsiTransportISCSI   OBJECT-IDENTITY
      STATUS   current
   ::= { scsiTransportTypes 5 }

   scsiTransportSBP  OBJECT-IDENTITY
      STATUS   current
   ::= { scsiTransportTypes 6 }

   scsiTransportSAS  OBJECT-IDENTITY
      STATUS   current
   ::= { scsiTransportTypes 7 }

   scsiInstanceTable OBJECT-TYPE
      SYNTAX      SEQUENCE OF ScsiInstanceEntry
      MAX-ACCESS  not-accessible
      STATUS      current
   ::= { scsiGeneral 1 }

   scsiInstanceEntry OBJECT-TYPE
      SYNTAX         ScsiInstanceEntry
      MAX-ACCESS     not-accessible
      STATUS         current
      INDEX { scsiInstIndex }
   ::= { scsiInstanceTable 1 }






   ScsiInstanceEntry ::= SEQUENCE {
      scsiInstIndex              ScsiIndexValue,
      scsiInstAlias              SnmpAdminString,
      scsiInstSoftwareIndex      ScsiHrSWInstalledIndexOrZero,
      scsiInstVendorVersion      SnmpAdminString,
      scsiInstScsiNotificationsEnable  TruthValue,
      scsiInstStorageType        StorageType
   }

   scsiInstIndex OBJECT-TYPE
      SYNTAX      ScsiIndexValue
      MAX-ACCESS  not-accessible
      STATUS      current
   ::= { scsiInstanceEntry 1 }

   scsiInstAlias OBJECT-TYPE
      SYNTAX      SnmpAdminString (SIZE(0..79))
      MAX-ACCESS  read-write
      STATUS      current
   ::= { scsiInstanceEntry 2 }

   scsiInstSoftwareIndex    OBJECT-TYPE
      SYNTAX      ScsiHrSWInstalledIndexOrZero
      MAX-ACCESS  read-only
      STATUS      current
   ::= { scsiInstanceEntry 3 }

   scsiInstVendorVersion OBJECT-TYPE
      SYNTAX      SnmpAdminString
      MAX-ACCESS  read-only
      STATUS      current
   ::= { scsiInstanceEntry 4 }

   scsiInstScsiNotificationsEnable  OBJECT-TYPE
      SYNTAX      TruthValue
      MAX-ACCESS  read-write
      STATUS      current
      DEFVAL { true }
   ::= { scsiInstanceEntry 5 }

   scsiInstStorageType OBJECT-TYPE
       SYNTAX       StorageType
       MAX-ACCESS   read-write
       STATUS       current
       DEFVAL { nonVolatile }
   ::= { scsiInstanceEntry 6 }


   scsiDeviceTable  OBJECT-TYPE
      SYNTAX           SEQUENCE OF ScsiDeviceEntry





      MAX-ACCESS       not-accessible
      STATUS           current
   ::= { scsiGeneral 2 }

   scsiDeviceEntry OBJECT-TYPE
      SYNTAX         ScsiDeviceEntry
      MAX-ACCESS     not-accessible
      STATUS         current
      INDEX {scsiInstIndex, scsiDeviceIndex}
   ::= { scsiDeviceTable 1 }

   ScsiDeviceEntry ::= SEQUENCE {
      scsiDeviceIndex      ScsiIndexValue,
      scsiDeviceAlias      SnmpAdminString,
      scsiDeviceRole       BITS,
      scsiDevicePortNumber Unsigned32
   }

   scsiDeviceIndex OBJECT-TYPE
      SYNTAX      ScsiIndexValue
      MAX-ACCESS  not-accessible
      STATUS      current
   ::= { scsiDeviceEntry 1 }

   scsiDeviceAlias OBJECT-TYPE
      SYNTAX      SnmpAdminString (SIZE(0..79))
      MAX-ACCESS  read-write
      STATUS      current
   ::= { scsiDeviceEntry 2 }

   scsiDeviceRole OBJECT-TYPE





      SYNTAX      BITS {
            target(0),
            initiator(1)
      }
      MAX-ACCESS  read-only
      STATUS      current
   ::= { scsiDeviceEntry 3 }

   scsiDevicePortNumber OBJECT-TYPE
      SYNTAX      Unsigned32
      MAX-ACCESS  read-only
      STATUS      current
   ::= { scsiDeviceEntry 4 }


   scsiPortTable  OBJECT-TYPE
      SYNTAX  SEQUENCE OF ScsiPortEntry
      MAX-ACCESS       not-accessible
      STATUS           current
   ::= { scsiGeneral 3 }

   scsiPortEntry OBJECT-TYPE
      SYNTAX            ScsiPortEntry
      MAX-ACCESS        not-accessible
      STATUS            current
      INDEX { scsiInstIndex, scsiDeviceIndex, scsiPortIndex }
   ::= { scsiPortTable  1 }

   ScsiPortEntry ::= SEQUENCE {
      scsiPortIndex        ScsiIndexValue,
      scsiPortRole         BITS,
      scsiPortTransportPtr    RowPointer,
      scsiPortBusyStatuses Counter32
   }






   scsiPortIndex OBJECT-TYPE
      SYNTAX      ScsiIndexValue
      MAX-ACCESS  not-accessible
      STATUS      current
   ::= { scsiPortEntry 1 }

   scsiPortRole OBJECT-TYPE
      SYNTAX      BITS {
            target(0),
            initiator(1)
      }
      MAX-ACCESS  read-only
      STATUS      current
   ::= { scsiPortEntry 2 }

   scsiPortTransportPtr OBJECT-TYPE
      SYNTAX      RowPointer
      MAX-ACCESS  read-only
      STATUS      current
   ::= { scsiPortEntry 3 }

   scsiPortBusyStatuses OBJECT-TYPE
      SYNTAX      Counter32
      MAX-ACCESS  read-only
      STATUS      current
   ::= { scsiPortEntry 4 }


   scsiTransportTable OBJECT-TYPE
      SYNTAX      SEQUENCE OF ScsiTransportEntry
      MAX-ACCESS  not-accessible





      STATUS      current
   ::= { scsiGeneral 5 }

   scsiTransportEntry OBJECT-TYPE
      SYNTAX      ScsiTransportEntry
      MAX-ACCESS  not-accessible
      STATUS      current
      INDEX { scsiInstIndex, scsiDeviceIndex, scsiTransportIndex}
   ::= { scsiTransportTable 1 }

   ScsiTransportEntry ::= SEQUENCE {
      scsiTransportIndex   ScsiIndexValue,
      scsiTransportType    AutonomousType,
      scsiTransportPointer RowPointer,
      scsiTransportDevName ScsiName
   }

   scsiTransportIndex OBJECT-TYPE
      SYNTAX      ScsiIndexValue
      MAX-ACCESS  not-accessible
      STATUS      current
   ::= { scsiTransportEntry 1 }

   scsiTransportType OBJECT-TYPE
      SYNTAX      AutonomousType
      MAX-ACCESS  read-only
      STATUS      current
   ::= { scsiTransportEntry 2 }

   scsiTransportPointer OBJECT-TYPE
      SYNTAX      RowPointer
      MAX-ACCESS  read-only





      STATUS      current
   ::= { scsiTransportEntry 3 }

   scsiTransportDevName OBJECT-TYPE
      SYNTAX      ScsiName
      MAX-ACCESS  read-only
      STATUS      current
   ::= { scsiTransportEntry 4 }

   scsiIntrDevTable  OBJECT-TYPE
      SYNTAX           SEQUENCE OF ScsiIntrDevEntry
      MAX-ACCESS       not-accessible
      STATUS           current
   ::= { scsiInitiatorDevice 1}

   scsiIntrDevEntry OBJECT-TYPE
      SYNTAX           ScsiIntrDevEntry
      MAX-ACCESS       not-accessible
      STATUS           current
      INDEX { scsiInstIndex, scsiDeviceIndex }
   ::= { scsiIntrDevTable  1 }

   ScsiIntrDevEntry ::= SEQUENCE {
      scsiIntrDevTgtAccessMode   INTEGER,
      scsiIntrDevOutResets       Counter32
   }

   scsiIntrDevTgtAccessMode   OBJECT-TYPE
      SYNTAX      INTEGER {





            unknown(1),
            autoEnable(2),
            manualEnable(3)
      }
      MAX-ACCESS  read-write
      STATUS      current
   ::= { scsiIntrDevEntry 1 }

   scsiIntrDevOutResets OBJECT-TYPE
      SYNTAX      Counter32
      MAX-ACCESS  read-only
      STATUS      current
   ::= { scsiIntrDevEntry 2 }



   scsiIntrPortTable OBJECT-TYPE
      SYNTAX          SEQUENCE OF ScsiIntrPortEntry
      MAX-ACCESS      not-accessible
      STATUS          current
   ::= { scsiInitiatorDevice 2 }

   scsiIntrPortEntry OBJECT-TYPE
      SYNTAX          ScsiIntrPortEntry
      MAX-ACCESS      not-accessible
      STATUS          current
      INDEX { scsiInstIndex, scsiDeviceIndex, scsiPortIndex }
   ::= { scsiIntrPortTable 1 }

   ScsiIntrPortEntry ::= SEQUENCE {
      scsiIntrPortName           ScsiName,
      scsiIntrPortIdentifier     ScsiIdentifier,
      scsiIntrPortOutCommands    Counter32,
      scsiIntrPortWrittenMegaBytes  Counter32,
      scsiIntrPortReadMegaBytes  Counter32,
      scsiIntrPortHSOutCommands  Counter64
   }

   scsiIntrPortName OBJECT-TYPE
      SYNTAX      ScsiName
      MAX-ACCESS  read-only
      STATUS      current
   ::= { scsiIntrPortEntry 1 }


   scsiIntrPortIdentifier OBJECT-TYPE
      SYNTAX      ScsiIdentifier
      MAX-ACCESS  read-only
      STATUS      current
   ::= { scsiIntrPortEntry 2 }

   scsiIntrPortOutCommands OBJECT-TYPE
      SYNTAX      Counter32
      UNITS       "commands"





      MAX-ACCESS  read-only
      STATUS      current
   ::= { scsiIntrPortEntry 3 }

   scsiIntrPortWrittenMegaBytes  OBJECT-TYPE
      SYNTAX      Counter32
      UNITS       "Megabytes"
      MAX-ACCESS  read-only
      STATUS      current
   ::= { scsiIntrPortEntry 4 }

   scsiIntrPortReadMegaBytes  OBJECT-TYPE
      SYNTAX      Counter32
      UNITS       "Megabytes"
      MAX-ACCESS  read-only
      STATUS      current
   ::= { scsiIntrPortEntry 5 }

   scsiIntrPortHSOutCommands  OBJECT-TYPE
      SYNTAX      Counter64
      UNITS       "commands"
      MAX-ACCESS  read-only
      STATUS      current
   ::= { scsiIntrPortEntry 6 }







   scsiRemoteTgtDev OBJECT IDENTIFIER ::= { scsiInitiatorDevice 3 }


   scsiDscTgtTable OBJECT-TYPE
      SYNTAX      SEQUENCE OF ScsiDscTgtEntry
      MAX-ACCESS  not-accessible
      STATUS      current
   ::= { scsiRemoteTgtDev 1 }

   scsiDscTgtEntry OBJECT-TYPE
      SYNTAX         ScsiDscTgtEntry
      MAX-ACCESS     not-accessible
      STATUS         current
      INDEX { scsiInstIndex, scsiDeviceIndex, scsiDscTgtIntrPortIndex,
      scsiDscTgtIndex }
   ::= { scsiDscTgtTable 1 }

   ScsiDscTgtEntry ::= SEQUENCE {
      scsiDscTgtIntrPortIndex ScsiPortIndexValueOrZero,
      scsiDscTgtIndex         ScsiIndexValue,
      scsiDscTgtDevOrPort     ScsiDeviceOrPort,
      scsiDscTgtName          ScsiName,
      scsiDscTgtConfigured    TruthValue,
      scsiDscTgtDiscovered    TruthValue,
      scsiDscTgtInCommands    Counter32,
      scsiDscTgtWrittenMegaBytes Counter32,
      scsiDscTgtReadMegaBytes Counter32,





      scsiDscTgtHSInCommands  Counter64,
      scsiDscTgtLastCreation  TimeStamp,
      scsiDscTgtRowStatus     RowStatus
   }

   scsiDscTgtIntrPortIndex OBJECT-TYPE
      SYNTAX      ScsiPortIndexValueOrZero
      MAX-ACCESS  not-accessible
      STATUS      current
   ::= { scsiDscTgtEntry 1 }

   scsiDscTgtIndex OBJECT-TYPE
      SYNTAX      ScsiIndexValue
      MAX-ACCESS  not-accessible
      STATUS      current
   ::= { scsiDscTgtEntry 2 }

   scsiDscTgtDevOrPort OBJECT-TYPE
      SYNTAX      ScsiDeviceOrPort
      MAX-ACCESS  read-create
      STATUS      current
   ::= { scsiDscTgtEntry 3 }

   scsiDscTgtName OBJECT-TYPE
      SYNTAX      ScsiName
      MAX-ACCESS  read-create
      STATUS      current
      ::= { scsiDscTgtEntry 4 }





   scsiDscTgtConfigured OBJECT-TYPE
      SYNTAX      TruthValue
      MAX-ACCESS  read-create
      STATUS      current
      DEFVAL { true }
   ::= { scsiDscTgtEntry 5 }

   scsiDscTgtDiscovered OBJECT-TYPE
      SYNTAX      TruthValue
      MAX-ACCESS  read-only
      STATUS      current
   ::= { scsiDscTgtEntry 6 }

   scsiDscTgtInCommands OBJECT-TYPE
      SYNTAX      Counter32
      UNITS       "commands"
      MAX-ACCESS  read-only
      STATUS      current
   ::= { scsiDscTgtEntry 7 }

   scsiDscTgtWrittenMegaBytes OBJECT-TYPE
      SYNTAX      Counter32
      UNITS       "Megabytes"
      MAX-ACCESS  read-only
      STATUS      current





   ::= { scsiDscTgtEntry 8 }

   scsiDscTgtReadMegaBytes OBJECT-TYPE
      SYNTAX      Counter32
      UNITS       "Megabytes"
      MAX-ACCESS  read-only
      STATUS      current
   ::= { scsiDscTgtEntry 9 }

   scsiDscTgtHSInCommands OBJECT-TYPE
      SYNTAX      Counter64
      UNITS       "commands"
      MAX-ACCESS  read-only
      STATUS      current
   ::= { scsiDscTgtEntry 10 }

   scsiDscTgtLastCreation OBJECT-TYPE
      SYNTAX      TimeStamp
      MAX-ACCESS  read-only
      STATUS      current
   ::= { scsiDscTgtEntry 11 }

   scsiDscTgtRowStatus OBJECT-TYPE
      SYNTAX      RowStatus
      MAX-ACCESS  read-create





      STATUS      current
   ::= { scsiDscTgtEntry 12 }


   scsiDscLunTable OBJECT-TYPE
      SYNTAX          SEQUENCE OF ScsiDscLunEntry
      MAX-ACCESS      not-accessible
      STATUS          current
   ::= { scsiRemoteTgtDev 2 }

   scsiDscLunEntry OBJECT-TYPE
      SYNTAX          ScsiDscLunEntry
      MAX-ACCESS      not-accessible
      STATUS          current





      INDEX { scsiInstIndex, scsiDeviceIndex, scsiDscTgtIntrPortIndex,
      scsiDscTgtIndex, scsiDscLunIndex }
   ::= { scsiDscLunTable 1 }

   ScsiDscLunEntry ::= SEQUENCE {
      scsiDscLunIndex   ScsiIndexValue,
      scsiDscLunLun     ScsiLUN
   }

   scsiDscLunIndex OBJECT-TYPE
      SYNTAX      ScsiIndexValue
      MAX-ACCESS  not-accessible
      STATUS      current
   ::= { scsiDscLunEntry 1 }

   scsiDscLunLun  OBJECT-TYPE
      SYNTAX      ScsiLUN
      MAX-ACCESS  read-only
      STATUS      current
   ::= { scsiDscLunEntry 2 }


   scsiDscLunIdTable OBJECT-TYPE
      SYNTAX          SEQUENCE OF ScsiDscLunIdEntry
      MAX-ACCESS      not-accessible
      STATUS          current
   ::= { scsiRemoteTgtDev 3 }

   scsiDscLunIdEntry OBJECT-TYPE
      SYNTAX           ScsiDscLunIdEntry
      MAX-ACCESS       not-accessible
      STATUS           current
      INDEX { scsiInstIndex, scsiDeviceIndex, scsiDscTgtIntrPortIndex,
      scsiDscTgtIndex, scsiDscLunIndex, scsiDscLunIdIndex }
   ::= { scsiDscLunIdTable 1 }

   ScsiDscLunIdEntry ::= SEQUENCE {
      scsiDscLunIdIndex       ScsiIndexValue,
      scsiDscLunIdCodeSet     ScsiIdCodeSet,
      scsiDscLunIdAssociation ScsiIdAssociation,
      scsiDscLunIdType        ScsiIdType,
      scsiDscLunIdValue       ScsiIdValue
   }

   scsiDscLunIdIndex OBJECT-TYPE
      SYNTAX      ScsiIndexValue
      MAX-ACCESS  not-accessible
      STATUS      current
   ::= { scsiDscLunIdEntry 1 }

   scsiDscLunIdCodeSet OBJECT-TYPE
      SYNTAX          ScsiIdCodeSet
      MAX-ACCESS      read-only
      STATUS          current
   ::= { scsiDscLunIdEntry 2 }

   scsiDscLunIdAssociation OBJECT-TYPE
      SYNTAX          ScsiIdAssociation
      MAX-ACCESS      read-only
      STATUS          current
   ::= { scsiDscLunIdEntry 3 }

   scsiDscLunIdType OBJECT-TYPE
      SYNTAX          ScsiIdType
      MAX-ACCESS      read-only
      STATUS          current
   ::= { scsiDscLunIdEntry 4 }

   scsiDscLunIdValue OBJECT-TYPE
      SYNTAX         ScsiIdValue
      MAX-ACCESS     read-only
      STATUS         current
   ::= { scsiDscLunIdEntry 5 }

   scsiAttTgtPortTable OBJECT-TYPE
      SYNTAX   SEQUENCE OF ScsiAttTgtPortEntry
      MAX-ACCESS  not-accessible





      STATUS      current
   ::= { scsiRemoteTgtDev 4 }

   scsiAttTgtPortEntry OBJECT-TYPE
      SYNTAX           ScsiAttTgtPortEntry
      MAX-ACCESS       not-accessible
      STATUS           current
      INDEX { scsiInstIndex, scsiDeviceIndex, scsiPortIndex,
      scsiAttTgtPortIndex }
   ::= { scsiAttTgtPortTable 1 }

   ScsiAttTgtPortEntry ::= SEQUENCE {
      scsiAttTgtPortIndex     ScsiIndexValue,
      scsiAttTgtPortDscTgtIdx ScsiIndexValueOrZero,
      scsiAttTgtPortName      ScsiName,
      scsiAttTgtPortIdentifier   ScsiIdentifier
   }

   scsiAttTgtPortIndex  OBJECT-TYPE
      SYNTAX      ScsiIndexValue
      MAX-ACCESS  not-accessible
      STATUS      current
   ::= { scsiAttTgtPortEntry 1 }

   scsiAttTgtPortDscTgtIdx OBJECT-TYPE
      SYNTAX      ScsiIndexValueOrZero
      MAX-ACCESS  read-only
      STATUS      current





   ::= { scsiAttTgtPortEntry 2 }

   scsiAttTgtPortName OBJECT-TYPE
      SYNTAX      ScsiName
      MAX-ACCESS  read-only
      STATUS      current
   ::= { scsiAttTgtPortEntry 3 }

   scsiAttTgtPortIdentifier OBJECT-TYPE
      SYNTAX      ScsiIdentifier
      MAX-ACCESS  read-only
      STATUS      current
   ::= { scsiAttTgtPortEntry 4 }

   scsiTgtDevTable OBJECT-TYPE
      SYNTAX   SEQUENCE OF ScsiTgtDevEntry
      MAX-ACCESS      not-accessible
      STATUS          current
   ::= { scsiTargetDevice 1 }

   scsiTgtDevEntry OBJECT-TYPE
      SYNTAX           ScsiTgtDevEntry
      MAX-ACCESS       not-accessible
      STATUS           current
      INDEX { scsiInstIndex, scsiDeviceIndex }
   ::= { scsiTgtDevTable 1 }

   ScsiTgtDevEntry ::= SEQUENCE {
      scsiTgtDevNumberOfLUs   Gauge32,
      scsiTgtDeviceStatus     INTEGER,
      scsiTgtDevNonAccessibleLUs Gauge32,
      scsiTgtDevResets        Counter32





   }

   scsiTgtDevNumberOfLUs OBJECT-TYPE
      SYNTAX      Gauge32
      MAX-ACCESS  read-only
      STATUS      current
   ::= { scsiTgtDevEntry 1 }

   scsiTgtDeviceStatus  OBJECT-TYPE
      SYNTAX      INTEGER {
         unknown(1),
         available(2),
         broken(3),
         readying(4),
         abnormal(5),
         nonAddrFailure(6),
         nonAddrFailReadying(7),
         nonAddrFailAbnormal(8)
      }
      MAX-ACCESS  read-only
      STATUS      current
   ::= { scsiTgtDevEntry 2}

   scsiTgtDevNonAccessibleLUs OBJECT-TYPE
      SYNTAX      Gauge32
      MAX-ACCESS  read-only
      STATUS      current
   ::= { scsiTgtDevEntry 3 }

   scsiTgtDevResets     OBJECT-TYPE
      SYNTAX      Counter32
      MAX-ACCESS  read-only
      STATUS      current
   ::= { scsiTgtDevEntry 4 }


   scsiTgtPortTable OBJECT-TYPE
      SYNTAX   SEQUENCE OF ScsiTgtPortEntry
      MAX-ACCESS  not-accessible
      STATUS      current





   ::= { scsiTargetDevice 2 }

   scsiTgtPortEntry OBJECT-TYPE
      SYNTAX   ScsiTgtPortEntry
      MAX-ACCESS  not-accessible
      STATUS      current
      INDEX { scsiInstIndex, scsiDeviceIndex, scsiPortIndex}
   ::= { scsiTgtPortTable 1 }

   ScsiTgtPortEntry ::= SEQUENCE {
      scsiTgtPortName         ScsiName,
      scsiTgtPortIdentifier   ScsiIdentifier,
      scsiTgtPortInCommands   Counter32,
      scsiTgtPortWrittenMegaBytes   Counter32,
      scsiTgtPortReadMegaBytes   Counter32,
      scsiTgtPortHSInCommands Counter64
   }

   scsiTgtPortName OBJECT-TYPE
      SYNTAX      ScsiName
      MAX-ACCESS  read-only
      STATUS      current
   ::= { scsiTgtPortEntry 1 }

   scsiTgtPortIdentifier OBJECT-TYPE
      SYNTAX      ScsiIdentifier
      MAX-ACCESS  read-only
      STATUS      current
   ::= { scsiTgtPortEntry 2 }

   scsiTgtPortInCommands OBJECT-TYPE
      SYNTAX      Counter32
      UNITS    "commands"
      MAX-ACCESS  read-only
      STATUS      current
   ::= { scsiTgtPortEntry 3 }

   scsiTgtPortWrittenMegaBytes OBJECT-TYPE
      SYNTAX      Counter32
      UNITS    "Megabytes"
      MAX-ACCESS  read-only
      STATUS      current
   ::= { scsiTgtPortEntry 4 }

   scsiTgtPortReadMegaBytes OBJECT-TYPE
      SYNTAX      Counter32
      UNITS    "Megabytes"
      MAX-ACCESS  read-only
      STATUS      current
   ::= { scsiTgtPortEntry 5 }

   scsiTgtPortHSInCommands OBJECT-TYPE
      SYNTAX      Counter64
      UNITS    "commands"
      MAX-ACCESS  read-only
      STATUS      current
   ::= { scsiTgtPortEntry 6 }

   scsiRemoteIntrDev OBJECT IDENTIFIER ::= { scsiTargetDevice 3 }






   scsiAuthorizedIntrTable OBJECT-TYPE
      SYNTAX   SEQUENCE OF ScsiAuthorizedIntrEntry
      MAX-ACCESS  not-accessible
      STATUS      current
   ::= { scsiRemoteIntrDev 1 }

   scsiAuthorizedIntrEntry OBJECT-TYPE
      SYNTAX      ScsiAuthorizedIntrEntry
      MAX-ACCESS  not-accessible
      STATUS      current
      INDEX { scsiInstIndex, scsiDeviceIndex, scsiAuthIntrTgtPortIndex,
      scsiAuthIntrIndex }
   ::= { scsiAuthorizedIntrTable 1 }

   ScsiAuthorizedIntrEntry ::= SEQUENCE {
      scsiAuthIntrTgtPortIndex   ScsiPortIndexValueOrZero,
      scsiAuthIntrIndex          ScsiIndexValue,
      scsiAuthIntrDevOrPort      ScsiDeviceOrPort,
      scsiAuthIntrName           ScsiName,
      scsiAuthIntrLunMapIndex    ScsiIndexValueOrZero,
      scsiAuthIntrAttachedTimes  Counter32,
      scsiAuthIntrOutCommands    Counter32,
      scsiAuthIntrReadMegaBytes  Counter32,
      scsiAuthIntrWrittenMegaBytes  Counter32,
      scsiAuthIntrHSOutCommands  Counter64,
      scsiAuthIntrLastCreation   TimeStamp,
      scsiAuthIntrRowStatus      RowStatus
   }


   scsiAuthIntrTgtPortIndex OBJECT-TYPE
      SYNTAX      ScsiPortIndexValueOrZero





      MAX-ACCESS  not-accessible
      STATUS      current
   ::= { scsiAuthorizedIntrEntry 1 }

   scsiAuthIntrIndex OBJECT-TYPE
      SYNTAX      ScsiIndexValue
      MAX-ACCESS  not-accessible
      STATUS      current
   ::= { scsiAuthorizedIntrEntry 2 }

   scsiAuthIntrDevOrPort OBJECT-TYPE
      SYNTAX      ScsiDeviceOrPort
      MAX-ACCESS  read-create
      STATUS      current
   ::= { scsiAuthorizedIntrEntry 3 }

   scsiAuthIntrName OBJECT-TYPE
      SYNTAX      ScsiName
      MAX-ACCESS  read-create
      STATUS      current
   ::= { scsiAuthorizedIntrEntry 4 }

   scsiAuthIntrLunMapIndex OBJECT-TYPE
      SYNTAX      ScsiIndexValueOrZero
      MAX-ACCESS  read-create
      STATUS      current
   ::= { scsiAuthorizedIntrEntry 5 }

   scsiAuthIntrAttachedTimes  OBJECT-TYPE
      SYNTAX      Counter32
      UNITS    "Times"
      MAX-ACCESS  read-only
      STATUS      current
   ::= { scsiAuthorizedIntrEntry 6 }

   scsiAuthIntrOutCommands OBJECT-TYPE
      SYNTAX      Counter32
      UNITS    "commands"
      MAX-ACCESS  read-only
      STATUS      current
   ::= { scsiAuthorizedIntrEntry 7 }

   scsiAuthIntrReadMegaBytes  OBJECT-TYPE
      SYNTAX      Counter32
      UNITS    "Megabytes"
      MAX-ACCESS  read-only
      STATUS      current
   ::= { scsiAuthorizedIntrEntry 8 }

   scsiAuthIntrWrittenMegaBytes  OBJECT-TYPE
      SYNTAX      Counter32
      UNITS    "Megabytes"
      MAX-ACCESS  read-only
      STATUS      current
   ::= { scsiAuthorizedIntrEntry 9}

   scsiAuthIntrHSOutCommands  OBJECT-TYPE
      SYNTAX      Counter64
      UNITS    "commands"
      MAX-ACCESS  read-only
      STATUS      current
   ::= { scsiAuthorizedIntrEntry 10 }

   scsiAuthIntrLastCreation OBJECT-TYPE
      SYNTAX      TimeStamp
      MAX-ACCESS  read-only
      STATUS      current
   ::= { scsiAuthorizedIntrEntry 11 }

   scsiAuthIntrRowStatus OBJECT-TYPE
      SYNTAX      RowStatus
      MAX-ACCESS  read-create





      STATUS      current
   ::= { scsiAuthorizedIntrEntry 12 }



   scsiAttIntrPortTable OBJECT-TYPE
      SYNTAX  SEQUENCE OF ScsiAttIntrPortEntry
      MAX-ACCESS      not-accessible
      STATUS          current
   ::= { scsiRemoteIntrDev 2 }

   scsiAttIntrPortEntry OBJECT-TYPE
      SYNTAX          ScsiAttIntrPortEntry
      MAX-ACCESS      not-accessible
      STATUS          current
      INDEX { scsiInstIndex, scsiDeviceIndex, scsiPortIndex,
      scsiAttIntrPortIndex }
   ::= { scsiAttIntrPortTable 1 }

   ScsiAttIntrPortEntry ::= SEQUENCE {
      scsiAttIntrPortIndex    ScsiIndexValue,
      scsiAttIntrPortAuthIntrIdx ScsiIndexValueOrZero,
      scsiAttIntrPortName     ScsiName,
      scsiAttIntrPortIdentifier       ScsiIdentifier
   }





   scsiAttIntrPortIndex OBJECT-TYPE
      SYNTAX      ScsiIndexValue
      MAX-ACCESS  not-accessible
      STATUS      current
   ::= { scsiAttIntrPortEntry 1 }

   scsiAttIntrPortAuthIntrIdx OBJECT-TYPE
      SYNTAX      ScsiIndexValueOrZero
      MAX-ACCESS  read-only
      STATUS      current
   ::= { scsiAttIntrPortEntry 2 }

   scsiAttIntrPortName OBJECT-TYPE
      SYNTAX      ScsiName
      MAX-ACCESS  read-only
      STATUS      current
   ::= { scsiAttIntrPortEntry 3 }

   scsiAttIntrPortIdentifier OBJECT-TYPE
      SYNTAX      ScsiIdentifier
      MAX-ACCESS  read-only
      STATUS      current
   ::= { scsiAttIntrPortEntry 4 }

   scsiLuTable OBJECT-TYPE
      SYNTAX   SEQUENCE OF ScsiLuEntry
      MAX-ACCESS  not-accessible
      STATUS      current
   ::= { scsiLogicalUnit 1 }

   scsiLuEntry OBJECT-TYPE
      SYNTAX      ScsiLuEntry
      MAX-ACCESS  not-accessible
      STATUS      current
      INDEX { scsiInstIndex, scsiDeviceIndex, scsiLuIndex}
   ::= { scsiLuTable 1 }

   ScsiLuEntry ::= SEQUENCE {
      scsiLuIndex          ScsiIndexValue,
      scsiLuDefaultLun     ScsiLUN,
      scsiLuWwnName        ScsiLuNameOrZero,
      scsiLuVendorId       SnmpAdminString,
      scsiLuProductId      SnmpAdminString,
      scsiLuRevisionId     SnmpAdminString,
      scsiLuPeripheralType Unsigned32,
      scsiLuStatus         INTEGER,
      scsiLuState          BITS,
      scsiLuInCommands     Counter32,
      scsiLuReadMegaBytes  Counter32,
      scsiLuWrittenMegaBytes     Counter32,
      scsiLuInResets       Counter32,
      scsiLuOutTaskSetFullStatus    Counter32,
      scsiLuHSInCommands   Counter64,
      scsiLuLastCreation   TimeStamp
   }

   scsiLuIndex OBJECT-TYPE
      SYNTAX      ScsiIndexValue
      MAX-ACCESS  not-accessible
      STATUS      current





   ::= { scsiLuEntry 1 }

   scsiLuDefaultLun OBJECT-TYPE
      SYNTAX      ScsiLUN
      MAX-ACCESS  read-only
      STATUS      current
   ::= { scsiLuEntry 2 }

   scsiLuWwnName OBJECT-TYPE
      SYNTAX      ScsiLuNameOrZero
      MAX-ACCESS  read-only
      STATUS      current
   ::= { scsiLuEntry 3 }

   scsiLuVendorId OBJECT-TYPE
      SYNTAX      SnmpAdminString
      MAX-ACCESS  read-only
      STATUS      current
   ::= { scsiLuEntry 4 }

   scsiLuProductId OBJECT-TYPE
      SYNTAX      SnmpAdminString
      MAX-ACCESS  read-only
      STATUS      current
   ::= { scsiLuEntry 5 }

   scsiLuRevisionId OBJECT-TYPE





      SYNTAX      SnmpAdminString
      MAX-ACCESS  read-only
      STATUS      current
   ::= { scsiLuEntry 6 }

   scsiLuPeripheralType OBJECT-TYPE
      SYNTAX      Unsigned32
      MAX-ACCESS  read-only
      STATUS      current
   ::= { scsiLuEntry 7 }

   scsiLuStatus   OBJECT-TYPE
      SYNTAX      INTEGER {
         unknown(1),
         available(2),
         notAvailable(3),
         broken(4),
         readying(5),
         abnormal(6)
      }
      MAX-ACCESS  read-only
      STATUS      current
   ::= { scsiLuEntry 8 }

   scsiLuState OBJECT-TYPE
      SYNTAX      BITS {
         dataLost(0),
         dynamicReconfigurationInProgress(1),
         exposed(2),
         fractionallyExposed(3),
         partiallyExposed(4),
         protectedRebuild(5),
         protectionDisabled(6),
         rebuild(7),
         recalculate(8),
         spareInUse(9),
         verifyInProgress(10)
      }
      MAX-ACCESS  read-only
      STATUS      current
   ::= { scsiLuEntry 9 }

   scsiLuInCommands OBJECT-TYPE
      SYNTAX      Counter32
      UNITS       "commands"
      MAX-ACCESS  read-only
      STATUS      current
   ::= { scsiLuEntry 10 }

   scsiLuReadMegaBytes OBJECT-TYPE
      SYNTAX      Counter32
      UNITS       "Megabytes"
      MAX-ACCESS  read-only
      STATUS      current
   ::= { scsiLuEntry 11 }

   scsiLuWrittenMegaBytes OBJECT-TYPE
      SYNTAX      Counter32
      UNITS       "Megabytes"
      MAX-ACCESS  read-only





      STATUS      current
   ::= { scsiLuEntry 12 }

   scsiLuInResets OBJECT-TYPE
      SYNTAX      Counter32
      UNITS       "resets"
      MAX-ACCESS  read-only
      STATUS      current
   ::= { scsiLuEntry 13 }

   scsiLuOutTaskSetFullStatus    OBJECT-TYPE
      SYNTAX      Counter32
      MAX-ACCESS  read-only
      STATUS      current
   ::= { scsiLuEntry 14 }

   scsiLuHSInCommands OBJECT-TYPE
      SYNTAX      Counter64
      UNITS       "commands"
      MAX-ACCESS  read-only
      STATUS      current





   ::= { scsiLuEntry 15 }

   scsiLuLastCreation OBJECT-TYPE
      SYNTAX      TimeStamp
      MAX-ACCESS  read-only
      STATUS      current
   ::= { scsiLuEntry 16 }

   scsiLuIdTable OBJECT-TYPE
      SYNTAX  SEQUENCE OF ScsiLuIdEntry
      MAX-ACCESS       not-accessible
      STATUS           current
   ::= { scsiLogicalUnit 2 }

   scsiLuIdEntry OBJECT-TYPE
      SYNTAX      ScsiLuIdEntry
      MAX-ACCESS  not-accessible
      STATUS      current
      INDEX {scsiInstIndex, scsiDeviceIndex, scsiLuIndex, scsiLuIdIndex}
   ::= { scsiLuIdTable 1 }

   ScsiLuIdEntry ::= SEQUENCE {
      scsiLuIdIndex        ScsiIndexValue,
      scsiLuIdCodeSet      ScsiIdCodeSet,
      scsiLuIdAssociation  ScsiIdAssociation,
      scsiLuIdType         ScsiIdType,
      scsiLuIdValue        ScsiIdValue
   }





   scsiLuIdIndex  OBJECT-TYPE
      SYNTAX          ScsiIndexValue
      MAX-ACCESS      not-accessible
      STATUS          current
   ::= { scsiLuIdEntry 1 }

   scsiLuIdCodeSet OBJECT-TYPE
      SYNTAX           ScsiIdCodeSet
      MAX-ACCESS       read-only
      STATUS           current
   ::= { scsiLuIdEntry 2 }

   scsiLuIdAssociation OBJECT-TYPE
      SYNTAX           ScsiIdAssociation
      MAX-ACCESS       read-only
      STATUS           current
   ::= { scsiLuIdEntry 3 }

   scsiLuIdType   OBJECT-TYPE
      SYNTAX           ScsiIdType
      MAX-ACCESS       read-only
      STATUS           current
   ::= { scsiLuIdEntry 4 }

   scsiLuIdValue OBJECT-TYPE
      SYNTAX         ScsiIdValue
      MAX-ACCESS     read-only
      STATUS         current
   ::= { scsiLuIdEntry 5 }


   scsiLunMapTable OBJECT-TYPE
      SYNTAX   SEQUENCE OF ScsiLunMapEntry
      MAX-ACCESS  not-accessible
      STATUS      current
   ::= { scsiLogicalUnit 3 }

   scsiLunMapEntry OBJECT-TYPE
      SYNTAX          ScsiLunMapEntry
      MAX-ACCESS      not-accessible
      STATUS          current
      INDEX { scsiInstIndex, scsiDeviceIndex, scsiLunMapIndex,
      scsiLunMapLun}
   ::= { scsiLunMapTable 1 }

   ScsiLunMapEntry ::= SEQUENCE {
      scsiLunMapIndex      ScsiIndexValue,
      scsiLunMapLun        ScsiLUN,
      scsiLunMapLuIndex    ScsiIndexValue,
      scsiLunMapRowStatus  RowStatus
   }

   scsiLunMapIndex   OBJECT-TYPE
      SYNTAX           ScsiIndexValue
      MAX-ACCESS       not-accessible
      STATUS           current
   ::= { scsiLunMapEntry 1 }

   scsiLunMapLun     OBJECT-TYPE
      SYNTAX           ScsiLUN
      MAX-ACCESS       not-accessible
      STATUS           current
   ::= { scsiLunMapEntry 2 }


   scsiLunMapLuIndex OBJECT-TYPE
      SYNTAX         ScsiIndexValue
      MAX-ACCESS     read-create
      STATUS         current
   ::= { scsiLunMapEntry 3 }





   scsiLunMapRowStatus  OBJECT-TYPE
      SYNTAX          RowStatus
      MAX-ACCESS      read-create
      STATUS          current
   ::= { scsiLunMapEntry 4 }


   scsiNotificationsPrefix OBJECT IDENTIFIER
                                ::= { scsiNotifications 0 }

   scsiTgtDeviceStatusChanged NOTIFICATION-TYPE
      OBJECTS { scsiTgtDeviceStatus }
      STATUS  current
   ::= { scsiNotificationsPrefix 1 }

   scsiLuStatusChanged NOTIFICATION-TYPE
      OBJECTS { scsiLuStatus }
      STATUS  current
   ::= { scsiNotificationsPrefix 2 }



   scsiCompliances OBJECT IDENTIFIER ::= { scsiConformance 1 }

   scsiCompliance MODULE-COMPLIANCE





      STATUS current
      MODULE  -- this module
         MANDATORY-GROUPS {
            scsiDeviceGroup
        }

        OBJECT scsiInstAlias
        MIN-ACCESS read-only

        OBJECT scsiInstScsiNotificationsEnable
        MIN-ACCESS read-only

        OBJECT scsiDeviceAlias
        MIN-ACCESS read-only

        OBJECT scsiInstStorageType
        MIN-ACCESS   read-only


        GROUP scsiTargetDeviceGroup
        GROUP scsiLunMapGroup

        OBJECT scsiAuthIntrDevOrPort
        MIN-ACCESS   read-only

        OBJECT scsiAuthIntrName
        MIN-ACCESS   read-only

        OBJECT scsiAuthIntrLunMapIndex
        MIN-ACCESS   read-only

        OBJECT scsiAuthIntrRowStatus
        SYNTAX RowStatus { active(1) }
        MIN-ACCESS   read-only

        GROUP scsiTgtDevLuNotificationsGroup



        GROUP scsiInitiatorDeviceGroup

         OBJECT scsiIntrDevTgtAccessMode
         MIN-ACCESS read-only

         GROUP scsiDiscoveryGroup

         OBJECT scsiLunMapLuIndex
         MIN-ACCESS read-only






         OBJECT scsiLunMapRowStatus
         SYNTAX RowStatus { active(1) }
         MIN-ACCESS read-only

         OBJECT scsiDscTgtDevOrPort
         MIN-ACCESS read-only

         OBJECT scsiDscTgtName
         MIN-ACCESS read-only

         OBJECT scsiDscTgtConfigured
         SYNTAX TruthValue { false(2) }
         MIN-ACCESS read-only

         OBJECT scsiDscTgtRowStatus
         SYNTAX RowStatus { active(1) }
         MIN-ACCESS read-only


        GROUP scsiDeviceStatGroup


        GROUP scsiInitiatorDevStatsGroup






        GROUP scsiDiscoveryStatsGroup


        GROUP scsiTargetDevStatsGroup

        GROUP scsiLunMapStatsGroup


        GROUP scsiInitiatorDevHSStatsGroup

        GROUP scsiDiscoveryHSStatsGroup

        GROUP scsiTargetDevHSStatsGroup

        GROUP scsiLunMapHSStatsGroup
   ::= { scsiCompliances 1 }

   scsiGroups OBJECT IDENTIFIER ::= { scsiConformance 2 }

   scsiDeviceGroup OBJECT-GROUP
      OBJECTS {
         scsiInstAlias,
         scsiInstSoftwareIndex,
         scsiInstVendorVersion,
         scsiInstScsiNotificationsEnable,
         scsiInstStorageType,
         scsiDeviceAlias,
         scsiDeviceRole,
         scsiDevicePortNumber,
         scsiPortRole,
         scsiPortTransportPtr,
         scsiTransportType,
         scsiTransportPointer,
         scsiTransportDevName
      }
      STATUS current
   ::= { scsiGroups 1 }

   scsiInitiatorDeviceGroup OBJECT-GROUP
      OBJECTS {
         scsiIntrDevTgtAccessMode,
         scsiIntrPortName,
         scsiIntrPortIdentifier,
         scsiAttTgtPortDscTgtIdx,
         scsiAttTgtPortName,
         scsiAttTgtPortIdentifier
      }
      STATUS current





   ::= { scsiGroups 2 }

   scsiDiscoveryGroup OBJECT-GROUP
      OBJECTS {
         scsiDscTgtDevOrPort,
         scsiDscTgtName,
         scsiDscTgtConfigured,
         scsiDscTgtDiscovered,
         scsiDscTgtRowStatus,
         scsiDscTgtLastCreation,
         scsiDscLunLun,
         scsiDscLunIdCodeSet,
         scsiDscLunIdAssociation,
         scsiDscLunIdType,
         scsiDscLunIdValue
      }
      STATUS current
   ::= { scsiGroups 3 }

   scsiTargetDeviceGroup OBJECT-GROUP
      OBJECTS {
         scsiTgtDevNumberOfLUs,
         scsiTgtDeviceStatus,
         scsiTgtDevNonAccessibleLUs,
         scsiTgtPortName,
         scsiTgtPortIdentifier,
         scsiAttIntrPortAuthIntrIdx,
         scsiAttIntrPortName,
         scsiAttIntrPortIdentifier,
         scsiLuDefaultLun,
         scsiLuWwnName,
         scsiLuVendorId,
         scsiLuProductId,
         scsiLuRevisionId,
         scsiLuPeripheralType,
         scsiLuStatus,
         scsiLuState,
         scsiLuLastCreation,
         scsiLuIdCodeSet,
         scsiLuIdAssociation,
         scsiLuIdType,
         scsiLuIdValue
      }
      STATUS current
   ::= { scsiGroups 4 }

   scsiLunMapGroup OBJECT-GROUP
      OBJECTS {
         scsiLunMapLuIndex,
         scsiLunMapRowStatus,
         scsiAuthIntrDevOrPort,
         scsiAuthIntrName,
         scsiAuthIntrLunMapIndex,
         scsiAuthIntrLastCreation,
         scsiAuthIntrRowStatus
      }
      STATUS current
   ::= { scsiGroups 5}

   scsiTargetDevStatsGroup OBJECT-GROUP
      OBJECTS {
         scsiTgtDevResets,
         scsiTgtPortInCommands,
         scsiTgtPortWrittenMegaBytes,
         scsiTgtPortReadMegaBytes,
         scsiLuInCommands,
         scsiLuReadMegaBytes,
         scsiLuWrittenMegaBytes,
         scsiLuInResets,
         scsiLuOutTaskSetFullStatus
      }
      STATUS current
   ::= { scsiGroups 6}

   scsiTargetDevHSStatsGroup OBJECT-GROUP
      OBJECTS {
         scsiTgtPortHSInCommands,
         scsiLuHSInCommands
      }
      STATUS current





   ::= { scsiGroups 7}

   scsiLunMapStatsGroup OBJECT-GROUP
      OBJECTS {
         scsiAuthIntrAttachedTimes,
         scsiAuthIntrOutCommands,
         scsiAuthIntrReadMegaBytes,
         scsiAuthIntrWrittenMegaBytes
      }
      STATUS current
   ::= { scsiGroups 8}

   scsiLunMapHSStatsGroup OBJECT-GROUP
      OBJECTS {
         scsiAuthIntrHSOutCommands
      }
      STATUS current
   ::= { scsiGroups 9}

   scsiInitiatorDevStatsGroup OBJECT-GROUP
      OBJECTS {
         scsiIntrDevOutResets,
         scsiIntrPortOutCommands,
         scsiIntrPortWrittenMegaBytes,
         scsiIntrPortReadMegaBytes
      }
      STATUS current
   ::= { scsiGroups 10}

   scsiInitiatorDevHSStatsGroup OBJECT-GROUP
      OBJECTS {
         scsiIntrPortHSOutCommands
      }
      STATUS current
   ::= { scsiGroups 11}

   scsiDiscoveryStatsGroup OBJECT-GROUP
      OBJECTS {
         scsiDscTgtInCommands,
         scsiDscTgtReadMegaBytes,
         scsiDscTgtWrittenMegaBytes
      }
      STATUS current
   ::= { scsiGroups 12}

   scsiDiscoveryHSStatsGroup OBJECT-GROUP
      OBJECTS {
         scsiDscTgtHSInCommands
      }
      STATUS current
   ::= { scsiGroups 13}

   scsiDeviceStatGroup OBJECT-GROUP
      OBJECTS {
         scsiPortBusyStatuses
      }
      STATUS current
   ::= { scsiGroups 14 }

   scsiTgtDevLuNotificationsGroup NOTIFICATION-GROUP
      NOTIFICATIONS {
         scsiTgtDeviceStatusChanged,
         scsiLuStatusChanged
      }
      STATUS current
   ::= { scsiGroups 15 }





   END
