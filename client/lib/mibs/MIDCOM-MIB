MIDCOM-MIB DEFINITIONS ::= BEGIN

   IMPORTS
       MODULE-IDENTITY, OBJECT-TYPE,
       NOTIFICATION-TYPE, Unsigned32,
       Counter32, Gauge32, mib-2
           FROM SNMPv2-SMI                  -- RFC 2578

       TEXTUAL-CONVENTION, TruthValue,
       StorageType, RowStatus
           FROM SNMPv2-TC                   -- RFC 2579

       MODULE-COMPLIANCE, OBJECT-GROUP,
       NOTIFICATION-GROUP
           FROM SNMPv2-CONF                 -- RFC 2580

       SnmpAdminString
           FROM SNMP-FRAMEWORK-MIB          -- RFC 3411

       InetAddressType, InetAddress,
       InetPortNumber,
       InetAddressPrefixLength
           FROM INET-ADDRESS-MIB            -- RFC 4001







       InterfaceIndexOrZero
           FROM IF-MIB                      -- RFC 2863

       NatBindIdOrZero
           FROM NAT-MIB;                    -- RFC 4008

   midcomMIB MODULE-IDENTITY
       LAST-UPDATED "200708091011Z"  -- August 09, 2007
       ORGANIZATION "IETF Middlebox Communication Working Group"


       ::= { mib-2 171 }


   midcomNotifications   OBJECT IDENTIFIER ::= { midcomMIB 0 }
   midcomObjects         OBJECT IDENTIFIER ::= { midcomMIB 1 }
   midcomConformance     OBJECT IDENTIFIER ::= { midcomMIB 2 }

   midcomTransaction     OBJECT IDENTIFIER ::= { midcomObjects 1 }






   midcomConfig   OBJECT IDENTIFIER ::= { midcomObjects 2 }

   midcomMonitoring      OBJECT IDENTIFIER ::= { midcomObjects 3 }



   midcomRuleTable OBJECT-TYPE
       SYNTAX      SEQUENCE OF MidcomRuleEntry
       MAX-ACCESS  not-accessible
       STATUS      current
       ::= { midcomTransaction 3 }

   midcomRuleEntry OBJECT-TYPE
       SYNTAX      MidcomRuleEntry
       MAX-ACCESS  not-accessible
       STATUS      current





       INDEX { midcomRuleOwner, midcomGroupIndex, midcomRuleIndex }
       ::= { midcomRuleTable 1 }

   MidcomRuleEntry ::= SEQUENCE {
       midcomRuleOwner                   SnmpAdminString,
       midcomRuleIndex                   Unsigned32,
       midcomRuleAdminStatus             INTEGER,
       midcomRuleOperStatus              INTEGER,
       midcomRuleStorageType             StorageType,
       midcomRuleStorageTime             Unsigned32,
       midcomRuleError                   SnmpAdminString,
       midcomRuleInterface               InterfaceIndexOrZero,
       midcomRuleFlowDirection           INTEGER,
       midcomRuleMaxIdleTime             Unsigned32,
       midcomRuleTransportProtocol       Unsigned32,
       midcomRulePortRange               INTEGER,
       midcomRuleInternalIpVersion       InetAddressType,
       midcomRuleExternalIpVersion       InetAddressType,
       midcomRuleInternalIpAddr          InetAddress,
       midcomRuleInternalIpPrefixLength  InetAddressPrefixLength,
       midcomRuleInternalPort            InetPortNumber,
       midcomRuleExternalIpAddr          InetAddress,
       midcomRuleExternalIpPrefixLength  InetAddressPrefixLength,
       midcomRuleExternalPort            InetPortNumber,
       midcomRuleInsideIpAddr            InetAddress,
       midcomRuleInsidePort              InetPortNumber,
       midcomRuleOutsideIpAddr           InetAddress,
       midcomRuleOutsidePort             InetPortNumber,
       midcomRuleLifetime                Unsigned32,
       midcomRuleRowStatus               RowStatus
   }

   midcomRuleOwner OBJECT-TYPE
       SYNTAX      SnmpAdminString (SIZE (0..32))
       MAX-ACCESS  not-accessible
       STATUS      current
       ::= { midcomRuleEntry 1 }

   midcomRuleIndex OBJECT-TYPE
       SYNTAX      Unsigned32 (1..4294967295)
       MAX-ACCESS  not-accessible





       STATUS      current
       ::= { midcomRuleEntry 3 }

   midcomRuleAdminStatus OBJECT-TYPE
       SYNTAX      INTEGER {
                       reserve(1),
                       enable(2),
                       notSet(3)
                   }
       MAX-ACCESS  read-create
       STATUS      current
       DEFVAL { notSet }
       ::= { midcomRuleEntry 4 }

   midcomRuleOperStatus OBJECT-TYPE
       SYNTAX      INTEGER {
                       newEntry(1),
                       setting(2),
                       checkingRequest(3),
                       incorrectRequest(4),
                       processingRequest(5),





                       requestRejected(6),
                       reserved(7),
                       enabled(8),
                       timedOut(9),
                       terminatedOnRequest(10),
                       terminated(11),
                       genericError(12)
                   }
       MAX-ACCESS  read-only
       STATUS      current
       DEFVAL { newEntry }
       ::= { midcomRuleEntry 5 }

   midcomRuleStorageType OBJECT-TYPE
       SYNTAX      StorageType
       MAX-ACCESS  read-create
       STATUS      current





       DEFVAL { volatile }
       ::= { midcomRuleEntry 6 }

   midcomRuleStorageTime OBJECT-TYPE
       SYNTAX      Unsigned32
       UNITS       "seconds"
       MAX-ACCESS  read-create
       STATUS      current
       DEFVAL { 0 }
       ::= { midcomRuleEntry 7 }

   midcomRuleError OBJECT-TYPE
       SYNTAX      SnmpAdminString
       MAX-ACCESS  read-only
       STATUS      current
       DEFVAL { ''H }
       ::= { midcomRuleEntry 8 }

   midcomRuleInterface OBJECT-TYPE
       SYNTAX      InterfaceIndexOrZero
       MAX-ACCESS  read-create
       STATUS      current
       DEFVAL { 0 }
       ::= { midcomRuleEntry 9 }

   midcomRuleFlowDirection OBJECT-TYPE
       SYNTAX      INTEGER {
                       inbound(1),
                       outbound(2),
                       biDirectional(3)
                   }
       MAX-ACCESS  read-create
       STATUS      current
       DEFVAL { outbound }
       ::= { midcomRuleEntry 10 }

   midcomRuleMaxIdleTime OBJECT-TYPE
       SYNTAX      Unsigned32
       UNITS       "seconds"
       MAX-ACCESS  read-create
       STATUS      current
       DEFVAL { 0 }
       ::= { midcomRuleEntry 11 }

   midcomRuleTransportProtocol OBJECT-TYPE
       SYNTAX      Unsigned32 (0..255)
       MAX-ACCESS  read-create
       STATUS      current





       DEFVAL { 0 }
       ::= { midcomRuleEntry 12 }

   midcomRulePortRange OBJECT-TYPE
       SYNTAX      INTEGER {
                       single(1),
                       pair(2)
                   }
       MAX-ACCESS  read-create
       STATUS      current
       DEFVAL { single }





       ::= { midcomRuleEntry 13}

   midcomRuleInternalIpVersion OBJECT-TYPE
       SYNTAX      InetAddressType
       MAX-ACCESS  read-create
       STATUS      current
       DEFVAL { ipv4 }
       ::= { midcomRuleEntry 14 }

   midcomRuleExternalIpVersion OBJECT-TYPE
       SYNTAX      InetAddressType
       MAX-ACCESS  read-create
       STATUS      current
       DEFVAL { ipv4 }
       ::= { midcomRuleEntry 15 }

   midcomRuleInternalIpAddr OBJECT-TYPE
       SYNTAX      InetAddress
       MAX-ACCESS  read-create
       STATUS      current
       ::= { midcomRuleEntry 16 }

   midcomRuleInternalIpPrefixLength OBJECT-TYPE
       SYNTAX      InetAddressPrefixLength
       MAX-ACCESS  read-create
       STATUS      current
       DEFVAL { 128 }
       ::= { midcomRuleEntry 17 }

   midcomRuleInternalPort OBJECT-TYPE
       SYNTAX      InetPortNumber
       MAX-ACCESS  read-create
       STATUS      current
       DEFVAL { 0 }
       ::= { midcomRuleEntry 18 }

   midcomRuleExternalIpAddr OBJECT-TYPE
       SYNTAX      InetAddress
       MAX-ACCESS  read-create
       STATUS      current





       ::= { midcomRuleEntry 19 }

   midcomRuleExternalIpPrefixLength OBJECT-TYPE
       SYNTAX      InetAddressPrefixLength
       MAX-ACCESS  read-create
       STATUS      current
       DEFVAL { 128 }
       ::= { midcomRuleEntry 20 }

   midcomRuleExternalPort OBJECT-TYPE
       SYNTAX      InetPortNumber
       MAX-ACCESS  read-create
       STATUS      current
       DEFVAL { 0 }
       ::= { midcomRuleEntry 21 }

   midcomRuleInsideIpAddr OBJECT-TYPE
       SYNTAX      InetAddress
       MAX-ACCESS  read-only
       STATUS      current
       ::= { midcomRuleEntry 22 }

   midcomRuleInsidePort OBJECT-TYPE
       SYNTAX      InetPortNumber
       MAX-ACCESS  read-only
       STATUS      current
       ::= { midcomRuleEntry 23 }

   midcomRuleOutsideIpAddr OBJECT-TYPE
       SYNTAX      InetAddress
       MAX-ACCESS  read-only
       STATUS      current
       ::= { midcomRuleEntry 24 }

   midcomRuleOutsidePort OBJECT-TYPE
       SYNTAX      InetPortNumber
       MAX-ACCESS  read-only
       STATUS      current
       ::= { midcomRuleEntry 25 }

   midcomRuleLifetime OBJECT-TYPE
       SYNTAX      Unsigned32
       UNITS       "seconds"
       MAX-ACCESS  read-create
       STATUS      current
       DEFVAL { 180 }
       ::= { midcomRuleEntry 26 }

   midcomRuleRowStatus OBJECT-TYPE
       SYNTAX      RowStatus
       MAX-ACCESS  read-create
       STATUS      current
       ::= { midcomRuleEntry 27 }


   midcomGroupTable OBJECT-TYPE
       SYNTAX      SEQUENCE OF MidcomGroupEntry
       MAX-ACCESS  not-accessible
       STATUS      current
       ::= { midcomTransaction 4 }

   midcomGroupEntry OBJECT-TYPE





       SYNTAX      MidcomGroupEntry
       MAX-ACCESS  not-accessible
       STATUS      current
       INDEX { midcomRuleOwner, midcomGroupIndex }
       ::= { midcomGroupTable 1 }

   MidcomGroupEntry ::= SEQUENCE {
       midcomGroupIndex      Unsigned32,
       midcomGroupLifetime   Unsigned32
   }

   midcomGroupIndex OBJECT-TYPE
       SYNTAX      Unsigned32 (1..4294967295)
       MAX-ACCESS  not-accessible
       STATUS      current
       ::= { midcomGroupEntry 2 }

   midcomGroupLifetime OBJECT-TYPE
       SYNTAX      Unsigned32
       UNITS       "seconds"
       MAX-ACCESS  read-write
       STATUS      current
       ::= { midcomGroupEntry 3 }



   midcomConfigMaxLifetime OBJECT-TYPE
       SYNTAX      Unsigned32
       UNITS       "seconds"





       MAX-ACCESS  read-write
       STATUS      current
       ::= { midcomConfig 1 }

   midcomConfigPersistentRules OBJECT-TYPE
       SYNTAX      TruthValue
       MAX-ACCESS  read-write
       STATUS      current
       ::= { midcomConfig 2 }

   midcomConfigIfTable OBJECT-TYPE
       SYNTAX      SEQUENCE OF MidcomConfigIfEntry
       MAX-ACCESS  not-accessible
       STATUS      current
       ::= { midcomConfig 3 }

   midcomConfigIfEntry OBJECT-TYPE
       SYNTAX      MidcomConfigIfEntry
       MAX-ACCESS  not-accessible
       STATUS      current





       INDEX { midcomConfigIfIndex }
       ::= { midcomConfigIfTable 1 }

   MidcomConfigIfEntry ::= SEQUENCE {
       midcomConfigIfIndex          InterfaceIndexOrZero,
       midcomConfigIfBits           BITS,
       midcomConfigIfEnabled        TruthValue
   }

   midcomConfigIfIndex OBJECT-TYPE
       SYNTAX      InterfaceIndexOrZero
       MAX-ACCESS  not-accessible
       STATUS      current
       ::= { midcomConfigIfEntry 1 }

   midcomConfigIfBits OBJECT-TYPE
       SYNTAX      BITS {
                       ipv4(0),
                       ipv6(1),
                       addressWildcards(2),
                       portWildcards(3),
                       firewall(4),
                       nat(5),
                       portTranslation(6),





                       protocolTranslation(7),
                       twiceNat(8),
                       inside(9)
                   }
       MAX-ACCESS  read-only
       STATUS      current
       ::= { midcomConfigIfEntry 2 }

   midcomConfigIfEnabled OBJECT-TYPE
       SYNTAX      TruthValue
       MAX-ACCESS  read-write
       STATUS      current
       DEFVAL { true }
       ::= { midcomConfigIfEntry 3 }


   midcomConfigFirewallTable OBJECT-TYPE
       SYNTAX      SEQUENCE OF MidcomConfigFirewallEntry
       MAX-ACCESS  not-accessible
       STATUS      current
       ::= { midcomConfig 4 }

   midcomConfigFirewallEntry OBJECT-TYPE
       SYNTAX      MidcomConfigFirewallEntry
       MAX-ACCESS  not-accessible
       STATUS      current
       INDEX { midcomConfigFirewallIndex }
       ::= { midcomConfigFirewallTable 1 }

   MidcomConfigFirewallEntry ::= SEQUENCE {
       midcomConfigFirewallIndex      InterfaceIndexOrZero,
       midcomConfigFirewallGroupId    SnmpAdminString,
       midcomConfigFirewallPriority   Unsigned32
   }

   midcomConfigFirewallIndex OBJECT-TYPE
       SYNTAX      InterfaceIndexOrZero
       MAX-ACCESS  not-accessible
       STATUS      current
       ::= { midcomConfigFirewallEntry 1 }

   midcomConfigFirewallGroupId OBJECT-TYPE
       SYNTAX      SnmpAdminString
       MAX-ACCESS  read-write
       STATUS      current
       ::= { midcomConfigFirewallEntry 2 }

   midcomConfigFirewallPriority OBJECT-TYPE
       SYNTAX      Unsigned32
       MAX-ACCESS  read-write
       STATUS      current
       ::= { midcomConfigFirewallEntry 3 }









   MidcomNatBindMode ::= TEXTUAL-CONVENTION
       STATUS      current
       SYNTAX      INTEGER {
                       addressBind(1),
                       addressPortBind(2),
                       none(3)
                   }

   MidcomNatSessionIdOrZero ::= TEXTUAL-CONVENTION
       DISPLAY-HINT "d"
       STATUS      current
       SYNTAX      Unsigned32


   midcomResourceTable OBJECT-TYPE
       SYNTAX      SEQUENCE OF MidcomResourceEntry
       MAX-ACCESS  not-accessible
       STATUS      current
       ::= { midcomMonitoring 1 }

   midcomResourceEntry OBJECT-TYPE
       SYNTAX      MidcomResourceEntry
       MAX-ACCESS  not-accessible
       STATUS      current
       AUGMENTS { midcomRuleEntry }
       ::= { midcomResourceTable 1 }

   MidcomResourceEntry ::= SEQUENCE {
       midcomRscNatInternalAddrBindMode   MidcomNatBindMode,
       midcomRscNatInternalAddrBindId     NatBindIdOrZero,
       midcomRscNatInsideAddrBindMode     MidcomNatBindMode,
       midcomRscNatInsideAddrBindId       NatBindIdOrZero,
       midcomRscNatSessionId1             MidcomNatSessionIdOrZero,
       midcomRscNatSessionId2             MidcomNatSessionIdOrZero,
       midcomRscFirewallRuleId            Unsigned32
   }

   midcomRscNatInternalAddrBindMode OBJECT-TYPE
       SYNTAX      MidcomNatBindMode
       MAX-ACCESS  read-only
       STATUS      current
       ::= { midcomResourceEntry 4 }

   midcomRscNatInternalAddrBindId OBJECT-TYPE
       SYNTAX      NatBindIdOrZero
       MAX-ACCESS  read-only
       STATUS      current
       ::= { midcomResourceEntry 5 }

   midcomRscNatInsideAddrBindMode OBJECT-TYPE
       SYNTAX      MidcomNatBindMode
       MAX-ACCESS  read-only
       STATUS      current
       ::= { midcomResourceEntry 6 }

   midcomRscNatInsideAddrBindId OBJECT-TYPE
       SYNTAX      NatBindIdOrZero
       MAX-ACCESS  read-only
       STATUS      current
       ::= { midcomResourceEntry 7 }

   midcomRscNatSessionId1 OBJECT-TYPE
       SYNTAX      MidcomNatSessionIdOrZero
       MAX-ACCESS  read-only





       STATUS      current
      ::= { midcomResourceEntry 8 }

   midcomRscNatSessionId2 OBJECT-TYPE
       SYNTAX      MidcomNatSessionIdOrZero
       MAX-ACCESS  read-only
       STATUS      current
       ::= { midcomResourceEntry 9 }

   midcomRscFirewallRuleId OBJECT-TYPE
       SYNTAX      Unsigned32
       MAX-ACCESS  read-only
       STATUS      current
       ::= { midcomResourceEntry 10 }


   midcomStatistics      OBJECT IDENTIFIER ::= { midcomMonitoring 2 }






   midcomCurrentOwners OBJECT-TYPE
       SYNTAX      Gauge32
       MAX-ACCESS  read-only
       STATUS      current
       ::= { midcomStatistics 1 }

   midcomTotalRejectedRuleEntries OBJECT-TYPE
       SYNTAX      Counter32
       MAX-ACCESS  read-only
       STATUS      current
       ::= { midcomStatistics 2 }

   midcomCurrentRulesIncomplete OBJECT-TYPE
       SYNTAX      Gauge32
       MAX-ACCESS  read-only
       STATUS      current
       ::= { midcomStatistics 3 }

   midcomTotalIncorrectReserveRules OBJECT-TYPE
       SYNTAX      Counter32
       MAX-ACCESS  read-only
       STATUS      current
       ::= { midcomStatistics 4 }

   midcomTotalRejectedReserveRules OBJECT-TYPE
       SYNTAX      Counter32
       MAX-ACCESS  read-only
       STATUS      current
       ::= { midcomStatistics 5 }





   midcomCurrentActiveReserveRules OBJECT-TYPE
       SYNTAX      Gauge32
       MAX-ACCESS  read-only
       STATUS      current
       ::= { midcomStatistics 6 }

   midcomTotalExpiredReserveRules OBJECT-TYPE
       SYNTAX      Counter32
       MAX-ACCESS  read-only
       STATUS      current
       ::= { midcomStatistics 7 }

   midcomTotalTerminatedOnRqReserveRules OBJECT-TYPE
       SYNTAX      Counter32
       MAX-ACCESS  read-only
       STATUS      current
       ::= { midcomStatistics 8 }

   midcomTotalTerminatedReserveRules OBJECT-TYPE
       SYNTAX      Counter32
       MAX-ACCESS  read-only
       STATUS      current
       ::= { midcomStatistics 9 }

   midcomTotalIncorrectEnableRules OBJECT-TYPE
       SYNTAX      Counter32
       MAX-ACCESS  read-only
       STATUS      current
       ::= { midcomStatistics 10 }

   midcomTotalRejectedEnableRules OBJECT-TYPE
       SYNTAX      Counter32





       MAX-ACCESS  read-only
       STATUS      current
       ::= { midcomStatistics 11 }
   midcomCurrentActiveEnableRules OBJECT-TYPE
       SYNTAX      Gauge32
       MAX-ACCESS  read-only
       STATUS      current
       ::= { midcomStatistics 12 }

   midcomTotalExpiredEnableRules OBJECT-TYPE
       SYNTAX      Counter32
       MAX-ACCESS  read-only
       STATUS      current
       ::= { midcomStatistics 13 }

   midcomTotalTerminatedOnRqEnableRules OBJECT-TYPE
       SYNTAX      Counter32
       MAX-ACCESS  read-only
       STATUS      current
       ::= { midcomStatistics 14 }

   midcomTotalTerminatedEnableRules OBJECT-TYPE
       SYNTAX      Counter32
       MAX-ACCESS  read-only
       STATUS      current
       ::= { midcomStatistics 15 }


   midcomUnsolicitedRuleEvent NOTIFICATION-TYPE





       OBJECTS     { midcomRuleOperStatus, midcomRuleLifetime }
       STATUS      current
       ::= { midcomNotifications 1 }

   midcomSolicitedRuleEvent NOTIFICATION-TYPE
       OBJECTS     { midcomRuleOperStatus, midcomRuleLifetime }
       STATUS      current
       ::= { midcomNotifications 2 }

   midcomSolicitedGroupEvent NOTIFICATION-TYPE
       OBJECTS     { midcomGroupLifetime }
       STATUS      current
       ::= { midcomNotifications 3 }







   midcomCompliances OBJECT IDENTIFIER ::= { midcomConformance 1 }
   midcomGroups      OBJECT IDENTIFIER ::= { midcomConformance 2 }




   midcomCompliance MODULE-COMPLIANCE
       STATUS      current
       MODULE      -- this module
       MANDATORY-GROUPS {
               midcomRuleGroup,
               midcomNotificationsGroup,
               midcomCapabilitiesGroup,
               midcomStatisticsGroup
       }
       GROUP   midcomConfigFirewallGroup
       GROUP   midcomResourceGroup
       OBJECT midcomRuleInternalIpPrefixLength
       MIN-ACCESS  read-only
       OBJECT midcomRuleExternalIpPrefixLength
       MIN-ACCESS  read-only
       OBJECT midcomRuleMaxIdleTime
       MIN-ACCESS  read-only
       OBJECT midcomRuleInterface
       MIN-ACCESS  read-only
       OBJECT midcomConfigMaxLifetime
       MIN-ACCESS  read-only
       OBJECT midcomConfigPersistentRules
       MIN-ACCESS  read-only
       OBJECT midcomConfigIfEnabled
       MIN-ACCESS  read-only
       OBJECT midcomConfigFirewallGroupId
       MIN-ACCESS  read-only
       OBJECT midcomConfigFirewallPriority
       MIN-ACCESS  read-only
       ::= { midcomCompliances 1 }

   midcomRuleGroup OBJECT-GROUP
       OBJECTS {
           midcomRuleAdminStatus,
           midcomRuleOperStatus,
           midcomRuleStorageType,
           midcomRuleStorageTime,
           midcomRuleError,
           midcomRuleInterface,
           midcomRuleFlowDirection,
           midcomRuleMaxIdleTime,
           midcomRuleTransportProtocol,
           midcomRulePortRange,
           midcomRuleInternalIpVersion,





           midcomRuleExternalIpVersion,
           midcomRuleInternalIpAddr,
           midcomRuleInternalIpPrefixLength,
           midcomRuleInternalPort,
           midcomRuleExternalIpAddr,
           midcomRuleExternalIpPrefixLength,
           midcomRuleExternalPort,
           midcomRuleInsideIpAddr,
           midcomRuleInsidePort,
           midcomRuleOutsideIpAddr,
           midcomRuleOutsidePort,
           midcomRuleLifetime,
           midcomRuleRowStatus,
           midcomGroupLifetime
       }
       STATUS      current
       ::= { midcomGroups 1 }

   midcomCapabilitiesGroup OBJECT-GROUP
       OBJECTS {
           midcomConfigMaxLifetime,
           midcomConfigPersistentRules,
           midcomConfigIfBits,
           midcomConfigIfEnabled
       }
       STATUS      current
       ::= { midcomGroups 2 }

   midcomConfigFirewallGroup OBJECT-GROUP
       OBJECTS {
           midcomConfigFirewallGroupId,
           midcomConfigFirewallPriority
       }
       STATUS      current
       ::= { midcomGroups 3 }

   midcomResourceGroup OBJECT-GROUP
       OBJECTS {





           midcomRscNatInternalAddrBindMode,
           midcomRscNatInternalAddrBindId,
           midcomRscNatInsideAddrBindMode,
           midcomRscNatInsideAddrBindId,
           midcomRscNatSessionId1,
           midcomRscNatSessionId2,
           midcomRscFirewallRuleId
       }
       STATUS      current
       ::= { midcomGroups 4 }

   midcomStatisticsGroup OBJECT-GROUP
       OBJECTS {
           midcomCurrentOwners,
           midcomTotalRejectedRuleEntries,
           midcomCurrentRulesIncomplete,
           midcomTotalIncorrectReserveRules,
           midcomTotalRejectedReserveRules,
           midcomCurrentActiveReserveRules,
           midcomTotalExpiredReserveRules,
           midcomTotalTerminatedOnRqReserveRules,
           midcomTotalTerminatedReserveRules,
           midcomTotalIncorrectEnableRules,
           midcomTotalRejectedEnableRules,
           midcomCurrentActiveEnableRules,
           midcomTotalExpiredEnableRules,
           midcomTotalTerminatedOnRqEnableRules,
           midcomTotalTerminatedEnableRules
       }
       STATUS      current
       ::= { midcomGroups 5 }
















   midcomNotificationsGroup NOTIFICATION-GROUP
        NOTIFICATIONS {
            midcomUnsolicitedRuleEvent,
            midcomSolicitedRuleEvent,
            midcomSolicitedGroupEvent
        }
        STATUS    current
        ::= { midcomGroups 6 }

   END
