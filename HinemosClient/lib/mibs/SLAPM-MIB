SLAPM-MIB DEFINITIONS ::= BEGIN

   IMPORTS
      MODULE-IDENTITY, OBJECT-TYPE,
      experimental, Integer32, NOTIFICATION-TYPE,
      Gauge32, Counter32, Unsigned32
          FROM SNMPv2-SMI                  -- RFC2578
      TEXTUAL-CONVENTION, RowStatus,
      TestAndIncr, DateAndTime
          FROM SNMPv2-TC                   -- RFC2579
      MODULE-COMPLIANCE, OBJECT-GROUP,
      NOTIFICATION-GROUP
          FROM SNMPv2-CONF                 -- RFC2580
      SnmpAdminString
          FROM SNMP-FRAMEWORK-MIB;         -- RFC2571

   slapmMIB MODULE-IDENTITY
      LAST-UPDATED "200001240000Z"          -- 24 January 2000
      ORGANIZATION "International Business Machines Corp."







      ::= { experimental 88 }


   SlapmNameType ::= TEXTUAL-CONVENTION
      STATUS  deprecated
      SYNTAX  SnmpAdminString (SIZE(0..32))

   SlapmStatus ::= TEXTUAL-CONVENTION
      STATUS  current
      SYNTAX  BITS {
                     slaMinInRateNotAchieved(0),
                     slaMaxInRateExceeded(1),
                     slaMaxDelayExceeded(2),
                     slaMinOutRateNotAchieved(3),
                     slaMaxOutRateExceeded(4),
                     monitorMinInRateNotAchieved(5),
                     monitorMaxInRateExceeded(6),
                     monitorMaxDelayExceeded(7),
                     monitorMinOutRateNotAchieved(8),
                     monitorMaxOutRateExceeded(9)





                   }

   SlapmPolicyRuleName ::= TEXTUAL-CONVENTION
      DISPLAY-HINT "1024t"
      STATUS  current
      SYNTAX  OCTET STRING (SIZE (0..1024))


   slapmNotifications  OBJECT IDENTIFIER ::= { slapmMIB 0 }
   slapmObjects        OBJECT IDENTIFIER ::= { slapmMIB 1 }
   slapmConformance    OBJECT IDENTIFIER ::= { slapmMIB 2 }


   slapmBaseObjects    OBJECT IDENTIFIER ::= { slapmObjects 1 }


   slapmSpinLock OBJECT-TYPE
      SYNTAX      TestAndIncr
      MAX-ACCESS  read-write
      STATUS      current
     ::= { slapmBaseObjects 1 }

   slapmPolicyCountQueries OBJECT-TYPE
      SYNTAX      Counter32
      MAX-ACCESS  read-only
      STATUS      current
      ::= { slapmBaseObjects 2 }

   slapmPolicyCountAccesses OBJECT-TYPE
      SYNTAX      Counter32
      MAX-ACCESS  read-only
      STATUS      current
      ::= { slapmBaseObjects 3 }

   slapmPolicyCountSuccessAccesses OBJECT-TYPE
      SYNTAX      Counter32
      MAX-ACCESS  read-only
      STATUS      current
      ::= { slapmBaseObjects 4 }

   slapmPolicyCountNotFounds OBJECT-TYPE
      SYNTAX      Counter32
      MAX-ACCESS  read-only
      STATUS      current
      ::= { slapmBaseObjects 5 }

   slapmPolicyPurgeTime OBJECT-TYPE
      SYNTAX      Integer32 (0..3600)  -- maximum of 1 hour
      UNITS       "seconds"
      MAX-ACCESS  read-write
      STATUS      current
      DEFVAL { 900 }  -- 15 minute default purge time
      ::= { slapmBaseObjects 6 }

   slapmPolicyTrapEnable OBJECT-TYPE
      SYNTAX      INTEGER { enabled(1), disabled(2) }
      MAX-ACCESS  read-write
      STATUS      current
      DEFVAL { disabled }
      ::= { slapmBaseObjects 7 }

   slapmPolicyTrapFilter   OBJECT-TYPE
      SYNTAX      Integer32 (0..64)
      UNITS       "intervals"





      MAX-ACCESS  read-write
      STATUS      current
      DEFVAL { 3 }
      ::= { slapmBaseObjects 8 }

   slapmTableObjects    OBJECT IDENTIFIER ::= { slapmObjects 2 }


   slapmPolicyStatsTable OBJECT-TYPE
      SYNTAX SEQUENCE OF SlapmPolicyStatsEntry
      MAX-ACCESS not-accessible
      STATUS deprecated
     ::= { slapmTableObjects 1 }

   slapmPolicyStatsEntry OBJECT-TYPE
      SYNTAX SlapmPolicyStatsEntry
      MAX-ACCESS not-accessible
      STATUS deprecated
      INDEX {
             slapmPolicyStatsSystemAddress,
             slapmPolicyStatsPolicyName,
             slapmPolicyStatsTrafficProfileName





            }
      ::= { slapmPolicyStatsTable 1 }

   SlapmPolicyStatsEntry ::=
      SEQUENCE {
          slapmPolicyStatsSystemAddress      OCTET STRING,
          slapmPolicyStatsPolicyName         SlapmNameType,
          slapmPolicyStatsTrafficProfileName SlapmNameType,
          slapmPolicyStatsOperStatus         INTEGER,
          slapmPolicyStatsActiveConns        Gauge32,
          slapmPolicyStatsTotalConns         Counter32,
          slapmPolicyStatsFirstActivated     DateAndTime,
          slapmPolicyStatsLastMapping        DateAndTime,
          slapmPolicyStatsInOctets           Counter32,
          slapmPolicyStatsOutOctets          Counter32,
          slapmPolicyStatsConnectionLimit    Integer32,
          slapmPolicyStatsCountAccepts       Counter32,
          slapmPolicyStatsCountDenies        Counter32,
          slapmPolicyStatsInDiscards         Counter32,
          slapmPolicyStatsOutDiscards        Counter32,
          slapmPolicyStatsInPackets          Counter32,
          slapmPolicyStatsOutPackets         Counter32,
          slapmPolicyStatsInProfileOctets    Counter32,
          slapmPolicyStatsOutProfileOctets   Counter32,
          slapmPolicyStatsMinRate            Integer32,
          slapmPolicyStatsMaxRate            Integer32,
          slapmPolicyStatsMaxDelay           Integer32
      }

   slapmPolicyStatsSystemAddress OBJECT-TYPE
      SYNTAX      OCTET STRING (SIZE(0 | 4 | 16))
      MAX-ACCESS  not-accessible
      STATUS      deprecated
      ::= { slapmPolicyStatsEntry 1 }

   slapmPolicyStatsPolicyName OBJECT-TYPE
      SYNTAX      SlapmNameType
      MAX-ACCESS  not-accessible
      STATUS      deprecated
      ::= { slapmPolicyStatsEntry 2 }





   slapmPolicyStatsTrafficProfileName OBJECT-TYPE
      SYNTAX      SlapmNameType
      MAX-ACCESS  not-accessible
      STATUS      deprecated
      ::= { slapmPolicyStatsEntry 3 }

   slapmPolicyStatsOperStatus OBJECT-TYPE
      SYNTAX      INTEGER {
                             inactive(1),
                             active(2),
                             deleteNeeded(3)
                          }
      MAX-ACCESS  read-only
      STATUS      deprecated
      ::= { slapmPolicyStatsEntry 4 }

   slapmPolicyStatsActiveConns OBJECT-TYPE
      SYNTAX      Gauge32
      MAX-ACCESS  read-only
      STATUS      deprecated
      ::= { slapmPolicyStatsEntry 5 }





   slapmPolicyStatsTotalConns OBJECT-TYPE
      SYNTAX      Counter32
      MAX-ACCESS  read-only
      STATUS      deprecated
      ::= { slapmPolicyStatsEntry 6 }

   slapmPolicyStatsFirstActivated OBJECT-TYPE
      SYNTAX      DateAndTime
      MAX-ACCESS  read-only
      STATUS      deprecated
      DEFVAL { '0000000000000000'H }
      ::= { slapmPolicyStatsEntry 7 }

   slapmPolicyStatsLastMapping OBJECT-TYPE
      SYNTAX      DateAndTime
      MAX-ACCESS  read-only
      STATUS      deprecated
      DEFVAL { '0000000000000000'H }
      ::= { slapmPolicyStatsEntry 8 }

   slapmPolicyStatsInOctets OBJECT-TYPE
      SYNTAX      Counter32
      MAX-ACCESS  read-only
      STATUS      deprecated
      ::= { slapmPolicyStatsEntry 9 }

   slapmPolicyStatsOutOctets OBJECT-TYPE
      SYNTAX      Counter32
      MAX-ACCESS  read-only
      STATUS      deprecated
      ::= { slapmPolicyStatsEntry 10 }

   slapmPolicyStatsConnectionLimit OBJECT-TYPE
      SYNTAX      Integer32
      MAX-ACCESS  read-only
      STATUS      deprecated
      ::= { slapmPolicyStatsEntry 11 }

   slapmPolicyStatsCountAccepts OBJECT-TYPE
      SYNTAX      Counter32
      MAX-ACCESS  read-only
      STATUS      deprecated
      ::= { slapmPolicyStatsEntry 12 }

   slapmPolicyStatsCountDenies OBJECT-TYPE
      SYNTAX      Counter32
      MAX-ACCESS  read-only
      STATUS      deprecated
      ::= { slapmPolicyStatsEntry 13 }

   slapmPolicyStatsInDiscards OBJECT-TYPE
      SYNTAX      Counter32
      MAX-ACCESS  read-only
      STATUS      deprecated
      ::= { slapmPolicyStatsEntry 14 }

   slapmPolicyStatsOutDiscards OBJECT-TYPE





      SYNTAX      Counter32
      MAX-ACCESS  read-only
      STATUS      deprecated
      ::= { slapmPolicyStatsEntry 15 }

   slapmPolicyStatsInPackets OBJECT-TYPE
      SYNTAX      Counter32
      MAX-ACCESS  read-only
      STATUS      deprecated
      ::= { slapmPolicyStatsEntry 16 }

   slapmPolicyStatsOutPackets OBJECT-TYPE
      SYNTAX      Counter32
      MAX-ACCESS  read-only
      STATUS      deprecated
      ::= { slapmPolicyStatsEntry 17 }

   slapmPolicyStatsInProfileOctets OBJECT-TYPE
      SYNTAX      Counter32
      MAX-ACCESS  read-only
      STATUS      deprecated
      ::= { slapmPolicyStatsEntry 18 }

   slapmPolicyStatsOutProfileOctets OBJECT-TYPE
      SYNTAX      Counter32
      MAX-ACCESS  read-only
      STATUS      deprecated
      ::= { slapmPolicyStatsEntry 19 }

   slapmPolicyStatsMinRate OBJECT-TYPE
      SYNTAX      Integer32
      UNITS       "Kilobits per second"





      MAX-ACCESS  read-only
      STATUS      deprecated
      ::= { slapmPolicyStatsEntry 20 }

   slapmPolicyStatsMaxRate OBJECT-TYPE
      SYNTAX      Integer32
      UNITS       "Kilobits per second"
      MAX-ACCESS  read-only
      STATUS      deprecated
      ::= { slapmPolicyStatsEntry 21 }

   slapmPolicyStatsMaxDelay OBJECT-TYPE
      SYNTAX      Integer32
      UNITS       "milliseconds"
      MAX-ACCESS  read-only
      STATUS      deprecated
      ::= { slapmPolicyStatsEntry 22 }


   slapmPolicyMonitorTable OBJECT-TYPE
      SYNTAX SEQUENCE OF SlapmPolicyMonitorEntry
      MAX-ACCESS not-accessible
      STATUS     deprecated
     ::= { slapmTableObjects 2 }

   slapmPolicyMonitorEntry OBJECT-TYPE
      SYNTAX     SlapmPolicyMonitorEntry
      MAX-ACCESS not-accessible
      STATUS     deprecated





      INDEX {
             slapmPolicyMonitorOwnerIndex,
             slapmPolicyMonitorSystemAddress,
             slapmPolicyMonitorPolicyName,
             slapmPolicyMonitorTrafficProfileName
            }
      ::= { slapmPolicyMonitorTable 1 }

   SlapmPolicyMonitorEntry ::=
      SEQUENCE {
          slapmPolicyMonitorOwnerIndex              SnmpAdminString,
          slapmPolicyMonitorSystemAddress           OCTET STRING,
          slapmPolicyMonitorPolicyName              SlapmNameType,
          slapmPolicyMonitorTrafficProfileName      SlapmNameType,
          slapmPolicyMonitorControl                 BITS,
          slapmPolicyMonitorStatus                  SlapmStatus,
          slapmPolicyMonitorInterval                Integer32,
          slapmPolicyMonitorIntTime                 DateAndTime,
          slapmPolicyMonitorCurrentInRate           Gauge32,
          slapmPolicyMonitorCurrentOutRate          Gauge32,
          slapmPolicyMonitorMinRateLow              Integer32,
          slapmPolicyMonitorMinRateHigh             Integer32,
          slapmPolicyMonitorMaxRateHigh             Integer32,
          slapmPolicyMonitorMaxRateLow              Integer32,
          slapmPolicyMonitorMaxDelayHigh            Integer32,
          slapmPolicyMonitorMaxDelayLow             Integer32,
          slapmPolicyMonitorMinInRateNotAchieves    Counter32,
          slapmPolicyMonitorMaxInRateExceeds        Counter32,
          slapmPolicyMonitorMaxDelayExceeds         Counter32,
          slapmPolicyMonitorMinOutRateNotAchieves   Counter32,
          slapmPolicyMonitorMaxOutRateExceeds       Counter32,
          slapmPolicyMonitorCurrentDelayRate        Gauge32,
          slapmPolicyMonitorRowStatus               RowStatus
      }

   slapmPolicyMonitorOwnerIndex OBJECT-TYPE
      SYNTAX      SnmpAdminString (SIZE(0..16))
      MAX-ACCESS  not-accessible
      STATUS      deprecated
      ::= { slapmPolicyMonitorEntry 1 }

   slapmPolicyMonitorSystemAddress OBJECT-TYPE
      SYNTAX      OCTET STRING (SIZE(0 | 4 | 16))
      MAX-ACCESS  not-accessible
      STATUS      deprecated
      ::= { slapmPolicyMonitorEntry 2 }

   slapmPolicyMonitorPolicyName OBJECT-TYPE
      SYNTAX      SlapmNameType
      MAX-ACCESS  not-accessible
      STATUS      deprecated
      ::= { slapmPolicyMonitorEntry 3 }

   slapmPolicyMonitorTrafficProfileName OBJECT-TYPE
      SYNTAX      SlapmNameType
      MAX-ACCESS  not-accessible
      STATUS      deprecated
      ::= { slapmPolicyMonitorEntry 4 }

   slapmPolicyMonitorControl OBJECT-TYPE
      SYNTAX      BITS {
                        monitorMinRate(0),
                        monitorMaxRate(1),





                        monitorMaxDelay(2),
                        enableAggregateTraps(3),
                        enableSubcomponentTraps(4),
                        monitorSubcomponents(5)
                       }
      MAX-ACCESS  read-create
      STATUS      deprecated
      DEFVAL   { { monitorMinRate, monitorMaxRate,
                   monitorMaxDelay } }
      ::= { slapmPolicyMonitorEntry 5 }

   slapmPolicyMonitorStatus OBJECT-TYPE
      SYNTAX      SlapmStatus
      MAX-ACCESS  read-only
      STATUS      deprecated
      ::= { slapmPolicyMonitorEntry 6 }

   slapmPolicyMonitorInterval OBJECT-TYPE
      SYNTAX      Integer32 (15..86400) -- 15 second min, 24 hour max
      UNITS       "seconds"
      MAX-ACCESS  read-create
      STATUS      deprecated
      DEFVAL   {20}    -- 20 seconds
      ::= { slapmPolicyMonitorEntry 7 }

   slapmPolicyMonitorIntTime OBJECT-TYPE
      SYNTAX      DateAndTime
      MAX-ACCESS  read-only
      STATUS      deprecated
      DEFVAL { '0000000000000000'H }
      ::= { slapmPolicyMonitorEntry 8 }

   slapmPolicyMonitorCurrentInRate OBJECT-TYPE
      SYNTAX      Gauge32
      UNITS       "kilobits per second"
      MAX-ACCESS  read-only
      STATUS      deprecated
      ::= { slapmPolicyMonitorEntry 9 }

   slapmPolicyMonitorCurrentOutRate OBJECT-TYPE





      SYNTAX      Gauge32
      UNITS       "kilobits per second"
      MAX-ACCESS  read-only
      STATUS      deprecated
      ::= { slapmPolicyMonitorEntry 10 }

   slapmPolicyMonitorMinRateLow OBJECT-TYPE
      SYNTAX      Integer32
      UNITS       "kilobits per second"
      MAX-ACCESS  read-create
      STATUS      deprecated
      ::= { slapmPolicyMonitorEntry 11 }

   slapmPolicyMonitorMinRateHigh OBJECT-TYPE
      SYNTAX      Integer32





      UNITS       "kilobits per second"
      MAX-ACCESS  read-create
      STATUS      deprecated
      ::= { slapmPolicyMonitorEntry 12 }

   slapmPolicyMonitorMaxRateHigh OBJECT-TYPE
      SYNTAX      Integer32
      UNITS       "kilobits per second"
      MAX-ACCESS  read-create
      STATUS      deprecated
      ::= { slapmPolicyMonitorEntry 13 }

   slapmPolicyMonitorMaxRateLow OBJECT-TYPE
      SYNTAX      Integer32
      UNITS       "kilobits per second"
      MAX-ACCESS  read-create
      STATUS      deprecated
      ::= { slapmPolicyMonitorEntry 14 }

   slapmPolicyMonitorMaxDelayHigh OBJECT-TYPE
      SYNTAX      Integer32
      UNITS       "milliseconds"
      MAX-ACCESS  read-create
      STATUS      deprecated
      ::= { slapmPolicyMonitorEntry 15 }

   slapmPolicyMonitorMaxDelayLow OBJECT-TYPE
      SYNTAX      Integer32
      UNITS       "milliseconds"
      MAX-ACCESS  read-create
      STATUS      deprecated





      ::= { slapmPolicyMonitorEntry 16 }

   slapmPolicyMonitorMinInRateNotAchieves OBJECT-TYPE
      SYNTAX      Counter32
      MAX-ACCESS  read-only
      STATUS      deprecated
      ::= { slapmPolicyMonitorEntry 17 }

   slapmPolicyMonitorMaxInRateExceeds OBJECT-TYPE
      SYNTAX      Counter32
      MAX-ACCESS  read-only
      STATUS      deprecated
      ::= { slapmPolicyMonitorEntry 18 }

   slapmPolicyMonitorMaxDelayExceeds OBJECT-TYPE
      SYNTAX      Counter32
      MAX-ACCESS  read-only
      STATUS      deprecated
      ::= { slapmPolicyMonitorEntry 19 }

   slapmPolicyMonitorMinOutRateNotAchieves OBJECT-TYPE
      SYNTAX      Counter32
      MAX-ACCESS  read-only
      STATUS      deprecated
      ::= { slapmPolicyMonitorEntry 20 }

   slapmPolicyMonitorMaxOutRateExceeds OBJECT-TYPE
      SYNTAX      Counter32
      MAX-ACCESS  read-only
      STATUS      deprecated
      ::= { slapmPolicyMonitorEntry 21 }

   slapmPolicyMonitorCurrentDelayRate OBJECT-TYPE





      SYNTAX      Gauge32
      UNITS       "milliseconds"
      MAX-ACCESS  read-only
      STATUS      deprecated
      ::= { slapmPolicyMonitorEntry 22 }

   slapmPolicyMonitorRowStatus  OBJECT-TYPE
      SYNTAX       RowStatus
      MAX-ACCESS   read-create
      STATUS       deprecated
      ::= { slapmPolicyMonitorEntry 23 }


   slapmSubcomponentTable OBJECT-TYPE
       SYNTAX      SEQUENCE OF SlapmSubcomponentEntry
       MAX-ACCESS  not-accessible
       STATUS      current
       ::= { slapmTableObjects 3 }

   slapmSubcomponentEntry OBJECT-TYPE
       SYNTAX      SlapmSubcomponentEntry
       MAX-ACCESS  not-accessible
       STATUS      current
       INDEX {
               slapmSubcomponentRemAddress,
               slapmSubcomponentRemPort,
               slapmSubcomponentLocalAddress,
               slapmSubcomponentLocalPort
             }
       ::= { slapmSubcomponentTable 1 }

   SlapmSubcomponentEntry ::=
       SEQUENCE {
            slapmSubcomponentRemAddress            OCTET STRING,
            slapmSubcomponentRemPort               Integer32,
            slapmSubcomponentLocalAddress          OCTET STRING,
            slapmSubcomponentLocalPort             Integer32,
            slapmSubcomponentProtocol              INTEGER,
            slapmSubcomponentSystemAddress         OCTET STRING,
            slapmSubcomponentPolicyName            SlapmNameType,
            slapmSubcomponentTrafficProfileName    SlapmNameType,
            slapmSubcomponentLastActivity          DateAndTime,
            slapmSubcomponentInOctets              Counter32,
            slapmSubcomponentOutOctets             Counter32,
            slapmSubcomponentTcpOutBufferedOctets  Counter32,
            slapmSubcomponentTcpInBufferedOctets   Counter32,
            slapmSubcomponentTcpReXmts             Counter32,
            slapmSubcomponentTcpRoundTripTime      Integer32,
            slapmSubcomponentTcpRoundTripVariance  Integer32,
            slapmSubcomponentInPdus                Counter32,
            slapmSubcomponentOutPdus               Counter32,
            slapmSubcomponentApplName              SnmpAdminString,
            slapmSubcomponentMonitorStatus         SlapmStatus,
            slapmSubcomponentMonitorIntTime        DateAndTime,
            slapmSubcomponentMonitorCurrentInRate  Gauge32,
            slapmSubcomponentMonitorCurrentOutRate Gauge32,
            slapmSubcomponentPolicyRuleIndex       Unsigned32
         }

   slapmSubcomponentRemAddress OBJECT-TYPE
      SYNTAX      OCTET STRING (SIZE(0 | 4 | 16))
      MAX-ACCESS  not-accessible
      STATUS      current
      ::= { slapmSubcomponentEntry 1 }

   slapmSubcomponentRemPort OBJECT-TYPE
      SYNTAX      Integer32(0..65535)
      MAX-ACCESS  not-accessible
      STATUS      current
      ::= { slapmSubcomponentEntry 2 }

   slapmSubcomponentLocalAddress OBJECT-TYPE
      SYNTAX      OCTET STRING (SIZE(4 | 16))
      MAX-ACCESS  not-accessible
      STATUS      current
      ::= { slapmSubcomponentEntry 3 }

   slapmSubcomponentLocalPort OBJECT-TYPE
      SYNTAX      Integer32(0..65535)
      MAX-ACCESS  not-accessible

      STATUS      current
      ::= { slapmSubcomponentEntry 4 }

   slapmSubcomponentProtocol OBJECT-TYPE
      SYNTAX      INTEGER {
                             udpListener(1),
                             tcpConnection(2)
                          }
      MAX-ACCESS  read-only
      STATUS      current
      ::= { slapmSubcomponentEntry 5 }

   slapmSubcomponentSystemAddress OBJECT-TYPE





      SYNTAX      OCTET STRING (SIZE(0 | 4 | 16))
      MAX-ACCESS  read-only
      STATUS      current
      ::= { slapmSubcomponentEntry 6 }

   slapmSubcomponentPolicyName OBJECT-TYPE
      SYNTAX      SlapmNameType
      MAX-ACCESS  read-only
      STATUS      deprecated
      ::= { slapmSubcomponentEntry 7 }

   slapmSubcomponentTrafficProfileName OBJECT-TYPE
      SYNTAX      SlapmNameType
      MAX-ACCESS  read-only
      STATUS      deprecated
      ::= { slapmSubcomponentEntry 8 }

  slapmSubcomponentLastActivity OBJECT-TYPE
      SYNTAX      DateAndTime
      MAX-ACCESS  read-only
      STATUS      current
      DEFVAL { '0000000000000000'H }
      ::= { slapmSubcomponentEntry 9 }

   slapmSubcomponentInOctets OBJECT-TYPE
       SYNTAX      Counter32





       MAX-ACCESS  read-only
       STATUS      current
       ::= { slapmSubcomponentEntry 10 }

   slapmSubcomponentOutOctets OBJECT-TYPE
       SYNTAX      Counter32
       MAX-ACCESS  read-only
       STATUS      current
       ::= { slapmSubcomponentEntry 11 }

   slapmSubcomponentTcpOutBufferedOctets OBJECT-TYPE
       SYNTAX      Counter32
       MAX-ACCESS  read-only
       STATUS      current
       ::= { slapmSubcomponentEntry 12 }

   slapmSubcomponentTcpInBufferedOctets OBJECT-TYPE
       SYNTAX      Counter32
       MAX-ACCESS  read-only
       STATUS      current
       ::= { slapmSubcomponentEntry 13 }

   slapmSubcomponentTcpReXmts OBJECT-TYPE
       SYNTAX      Counter32
       MAX-ACCESS  read-only
       STATUS      current
       ::= { slapmSubcomponentEntry 14 }

   slapmSubcomponentTcpRoundTripTime OBJECT-TYPE
       SYNTAX       Integer32
       UNITS        "milliseconds"





       MAX-ACCESS   read-only
       STATUS       current
       ::= { slapmSubcomponentEntry 15 }

   slapmSubcomponentTcpRoundTripVariance OBJECT-TYPE
       SYNTAX       Integer32
       MAX-ACCESS   read-only
       STATUS       current
       ::= { slapmSubcomponentEntry 16 }

   slapmSubcomponentInPdus OBJECT-TYPE
       SYNTAX       Counter32
       MAX-ACCESS   read-only
       STATUS       current
       ::= { slapmSubcomponentEntry 17 }

   slapmSubcomponentOutPdus OBJECT-TYPE
       SYNTAX       Counter32
       MAX-ACCESS   read-only
       STATUS       current
       ::= { slapmSubcomponentEntry 18 }

   slapmSubcomponentApplName OBJECT-TYPE
       SYNTAX       SnmpAdminString (SIZE(0..32))
       MAX-ACCESS   read-only
       STATUS       current
       ::= { slapmSubcomponentEntry 19 }

   slapmSubcomponentMonitorStatus OBJECT-TYPE
      SYNTAX      SlapmStatus
      MAX-ACCESS  read-only
      STATUS       current
      ::= { slapmSubcomponentEntry 20 }

   slapmSubcomponentMonitorIntTime OBJECT-TYPE
      SYNTAX      DateAndTime
      MAX-ACCESS  read-only
      STATUS      current
      DEFVAL { '0000000000000000'H }
      ::= { slapmSubcomponentEntry 21 }

   slapmSubcomponentMonitorCurrentInRate OBJECT-TYPE
      SYNTAX      Gauge32
      UNITS       "kilobits per second"
      MAX-ACCESS  read-only
      STATUS      current
      ::= { slapmSubcomponentEntry 22 }

   slapmSubcomponentMonitorCurrentOutRate OBJECT-TYPE
      SYNTAX      Gauge32
      UNITS       "kilobits per second"
      MAX-ACCESS  read-only
      STATUS      current
      ::= { slapmSubcomponentEntry 23 }

  slapmSubcomponentPolicyRuleIndex OBJECT-TYPE
     SYNTAX      Unsigned32 (0..4294967295)
     MAX-ACCESS  read-only
     STATUS      current
     ::= { slapmSubcomponentEntry 24 }


   slapmPolicyNameTable OBJECT-TYPE
      SYNTAX SEQUENCE OF SlapmPolicyNameEntry
      MAX-ACCESS not-accessible
      STATUS current
     ::= { slapmTableObjects 4 }

   slapmPolicyNameEntry OBJECT-TYPE
      SYNTAX SlapmPolicyNameEntry
      MAX-ACCESS not-accessible
      STATUS current
      INDEX {
             slapmPolicyNameSystemAddress,
             slapmPolicyNameIndex
            }
      ::= { slapmPolicyNameTable 1 }

   SlapmPolicyNameEntry ::=
      SEQUENCE {
          slapmPolicyNameSystemAddress   OCTET STRING,
          slapmPolicyNameIndex           Unsigned32,
          slapmPolicyNameOfRule          SlapmPolicyRuleName
      }

   slapmPolicyNameSystemAddress OBJECT-TYPE
      SYNTAX      OCTET STRING (SIZE(0 | 4 | 16))
      MAX-ACCESS  not-accessible
      STATUS      current
      ::= { slapmPolicyNameEntry 1 }

   slapmPolicyNameIndex OBJECT-TYPE
      SYNTAX      Unsigned32 (1..4294967295)
      MAX-ACCESS  not-accessible
      STATUS      current
      ::= { slapmPolicyNameEntry 2 }

   slapmPolicyNameOfRule OBJECT-TYPE
      SYNTAX      SlapmPolicyRuleName
      MAX-ACCESS  read-only
      STATUS      current
      ::= { slapmPolicyNameEntry 3 }


   slapmPolicyRuleStatsTable OBJECT-TYPE
      SYNTAX SEQUENCE OF SlapmPolicyRuleStatsEntry
      MAX-ACCESS not-accessible
      STATUS current
     ::= { slapmTableObjects 5 }

   slapmPolicyRuleStatsEntry OBJECT-TYPE
      SYNTAX SlapmPolicyRuleStatsEntry
      MAX-ACCESS not-accessible
      STATUS current
      INDEX {
             slapmPolicyNameSystemAddress,





             slapmPolicyNameIndex
            }
      ::= { slapmPolicyRuleStatsTable 1 }

   SlapmPolicyRuleStatsEntry ::=
      SEQUENCE {
          slapmPolicyRuleStatsOperStatus     INTEGER,
          slapmPolicyRuleStatsActiveConns    Gauge32,
          slapmPolicyRuleStatsTotalConns     Counter32,
          slapmPolicyRuleStatsLActivated     DateAndTime,
          slapmPolicyRuleStatsLastMapping    DateAndTime,
          slapmPolicyRuleStatsInOctets       Counter32,
          slapmPolicyRuleStatsOutOctets      Counter32,
          slapmPolicyRuleStatsConnLimit      Unsigned32,
          slapmPolicyRuleStatsCountAccepts   Counter32,
          slapmPolicyRuleStatsCountDenies    Counter32,
          slapmPolicyRuleStatsInDiscards     Counter32,
          slapmPolicyRuleStatsOutDiscards    Counter32,
          slapmPolicyRuleStatsInPackets      Counter32,
          slapmPolicyRuleStatsOutPackets     Counter32,
          slapmPolicyRuleStatsInProOctets    Counter32,
          slapmPolicyRuleStatsOutProOctets   Counter32,
          slapmPolicyRuleStatsMinRate        Unsigned32,
          slapmPolicyRuleStatsMaxRate        Unsigned32,
          slapmPolicyRuleStatsMaxDelay       Unsigned32,
          slapmPolicyRuleStatsTotalRsvpFlows Counter32,
          slapmPolicyRuleStatsActRsvpFlows   Gauge32
      }

   slapmPolicyRuleStatsOperStatus OBJECT-TYPE
      SYNTAX      INTEGER {
                             inactive(1),
                             active(2),
                             deleteNeeded(3)
                          }
      MAX-ACCESS  read-only
      STATUS      current
      ::= { slapmPolicyRuleStatsEntry 1 }

   slapmPolicyRuleStatsActiveConns OBJECT-TYPE
      SYNTAX      Gauge32
      MAX-ACCESS  read-only
      STATUS      current
      ::= { slapmPolicyRuleStatsEntry 2 }

   slapmPolicyRuleStatsTotalConns OBJECT-TYPE
      SYNTAX      Counter32
      MAX-ACCESS  read-only
      STATUS      current
      ::= { slapmPolicyRuleStatsEntry 3 }

   slapmPolicyRuleStatsLActivated OBJECT-TYPE
      SYNTAX      DateAndTime
      MAX-ACCESS  read-only
      STATUS      current
      DEFVAL { '0000000000000000'H }
      ::= { slapmPolicyRuleStatsEntry 4 }

   slapmPolicyRuleStatsLastMapping OBJECT-TYPE
      SYNTAX      DateAndTime
      MAX-ACCESS  read-only
      STATUS      current





      DEFVAL { '0000000000000000'H }
      ::= { slapmPolicyRuleStatsEntry 5 }

   slapmPolicyRuleStatsInOctets OBJECT-TYPE
      SYNTAX      Counter32
      MAX-ACCESS  read-only
      STATUS      current
      ::= { slapmPolicyRuleStatsEntry 6 }

   slapmPolicyRuleStatsOutOctets OBJECT-TYPE
      SYNTAX      Counter32
      MAX-ACCESS  read-only
      STATUS      current
      ::= { slapmPolicyRuleStatsEntry 7 }

   slapmPolicyRuleStatsConnLimit OBJECT-TYPE
      SYNTAX      Unsigned32
      MAX-ACCESS  read-only
      STATUS      current
      ::= { slapmPolicyRuleStatsEntry 8 }

   slapmPolicyRuleStatsCountAccepts OBJECT-TYPE
      SYNTAX      Counter32
      MAX-ACCESS  read-only
      STATUS      current
      ::= { slapmPolicyRuleStatsEntry 9 }

   slapmPolicyRuleStatsCountDenies OBJECT-TYPE
      SYNTAX      Counter32
      MAX-ACCESS  read-only





      STATUS      current
      ::= { slapmPolicyRuleStatsEntry 10 }

   slapmPolicyRuleStatsInDiscards OBJECT-TYPE
      SYNTAX      Counter32
      MAX-ACCESS  read-only
      STATUS      current
      ::= { slapmPolicyRuleStatsEntry 11 }

   slapmPolicyRuleStatsOutDiscards OBJECT-TYPE
      SYNTAX      Counter32
      MAX-ACCESS  read-only
      STATUS      current
      ::= { slapmPolicyRuleStatsEntry 12 }

   slapmPolicyRuleStatsInPackets OBJECT-TYPE
      SYNTAX      Counter32
      MAX-ACCESS  read-only
      STATUS      current
      ::= { slapmPolicyRuleStatsEntry 13 }

   slapmPolicyRuleStatsOutPackets OBJECT-TYPE
      SYNTAX      Counter32
      MAX-ACCESS  read-only
      STATUS      current
      ::= { slapmPolicyRuleStatsEntry 14 }






   slapmPolicyRuleStatsInProOctets OBJECT-TYPE
      SYNTAX      Counter32
      MAX-ACCESS  read-only
      STATUS      current
      ::= { slapmPolicyRuleStatsEntry 15 }

   slapmPolicyRuleStatsOutProOctets OBJECT-TYPE
      SYNTAX      Counter32
      MAX-ACCESS  read-only
      STATUS      current
      ::= { slapmPolicyRuleStatsEntry 16 }

   slapmPolicyRuleStatsMinRate OBJECT-TYPE
      SYNTAX      Unsigned32
      UNITS       "Kilobits per second"
      MAX-ACCESS  read-only
      STATUS      current
      ::= { slapmPolicyRuleStatsEntry 17 }

   slapmPolicyRuleStatsMaxRate OBJECT-TYPE
      SYNTAX      Unsigned32
      UNITS       "Kilobits per second"
      MAX-ACCESS  read-only
      STATUS      current
      ::= { slapmPolicyRuleStatsEntry 18 }

   slapmPolicyRuleStatsMaxDelay OBJECT-TYPE
      SYNTAX      Unsigned32
      UNITS       "milliseconds"
      MAX-ACCESS  read-only
      STATUS      current
      ::= { slapmPolicyRuleStatsEntry 19 }

   slapmPolicyRuleStatsTotalRsvpFlows OBJECT-TYPE
      SYNTAX      Counter32
      MAX-ACCESS  read-only





      STATUS      current
      ::= { slapmPolicyRuleStatsEntry 20 }

   slapmPolicyRuleStatsActRsvpFlows OBJECT-TYPE
      SYNTAX      Gauge32
      MAX-ACCESS  read-only
      STATUS      current
      ::= { slapmPolicyRuleStatsEntry 21 }


   slapmPRMonTable OBJECT-TYPE
      SYNTAX SEQUENCE OF SlapmPRMonEntry
      MAX-ACCESS not-accessible
      STATUS current
     ::= { slapmTableObjects 6 }

   slapmPRMonEntry OBJECT-TYPE
      SYNTAX SlapmPRMonEntry
      MAX-ACCESS not-accessible
      STATUS current
      INDEX {
             slapmPRMonOwnerIndex,
             slapmPRMonSystemAddress,
             slapmPRMonIndex
            }
      ::= { slapmPRMonTable 1 }

   SlapmPRMonEntry ::=
      SEQUENCE {
          slapmPRMonOwnerIndex              SnmpAdminString,
          slapmPRMonSystemAddress           OCTET STRING,
          slapmPRMonIndex                   Unsigned32,





          slapmPRMonControl                 BITS,
          slapmPRMonStatus                  SlapmStatus,
          slapmPRMonInterval                Unsigned32,
          slapmPRMonIntTime                 DateAndTime,
          slapmPRMonCurrentInRate           Gauge32,
          slapmPRMonCurrentOutRate          Gauge32,
          slapmPRMonMinRateLow              Unsigned32,
          slapmPRMonMinRateHigh             Unsigned32,
          slapmPRMonMaxRateHigh             Unsigned32,
          slapmPRMonMaxRateLow              Unsigned32,
          slapmPRMonMaxDelayHigh            Unsigned32,
          slapmPRMonMaxDelayLow             Unsigned32,
          slapmPRMonMinInRateNotAchieves    Counter32,
          slapmPRMonMaxInRateExceeds        Counter32,
          slapmPRMonMaxDelayExceeds         Counter32,
          slapmPRMonMinOutRateNotAchieves   Counter32,
          slapmPRMonMaxOutRateExceeds       Counter32,
          slapmPRMonCurrentDelayRate        Gauge32,
          slapmPRMonRowStatus               RowStatus
      }

   slapmPRMonOwnerIndex OBJECT-TYPE
      SYNTAX      SnmpAdminString (SIZE(0..16))
      MAX-ACCESS  not-accessible
      STATUS      current





      ::= { slapmPRMonEntry 1 }

   slapmPRMonSystemAddress OBJECT-TYPE
      SYNTAX      OCTET STRING (SIZE(0 | 4 | 16))
      MAX-ACCESS  not-accessible
      STATUS      current
      ::= { slapmPRMonEntry 2 }

   slapmPRMonIndex OBJECT-TYPE
      SYNTAX      Unsigned32
      MAX-ACCESS  not-accessible
      STATUS      current
      ::= { slapmPRMonEntry 3 }

   slapmPRMonControl OBJECT-TYPE
      SYNTAX      BITS {
                        monitorMinRate(0),
                        monitorMaxRate(1),
                        monitorMaxDelay(2),
                        enableAggregateTraps(3),
                        enableSubcomponentTraps(4),
                        monitorSubcomponents(5)
                       }
      MAX-ACCESS  read-create
      STATUS      current
      DEFVAL   { { monitorMinRate, monitorMaxRate,
                   monitorMaxDelay } }
      ::= { slapmPRMonEntry 4 }

   slapmPRMonStatus OBJECT-TYPE
      SYNTAX      SlapmStatus
      MAX-ACCESS  read-only
      STATUS      current
      ::= { slapmPRMonEntry 5 }

   slapmPRMonInterval OBJECT-TYPE
      SYNTAX      Unsigned32 (15..86400) -- 15 second min, 24 hour max
      UNITS       "seconds"
      MAX-ACCESS  read-create





      STATUS      current
      DEFVAL   {20}    -- 20 seconds
      ::= { slapmPRMonEntry 6 }

   slapmPRMonIntTime OBJECT-TYPE
      SYNTAX      DateAndTime
      MAX-ACCESS  read-only
      STATUS      current
      DEFVAL { '0000000000000000'H }
      ::= { slapmPRMonEntry 7 }

   slapmPRMonCurrentInRate OBJECT-TYPE
      SYNTAX      Gauge32
      UNITS       "kilobits per second"
      MAX-ACCESS  read-only
      STATUS      current
      ::= { slapmPRMonEntry 8 }

   slapmPRMonCurrentOutRate OBJECT-TYPE
      SYNTAX      Gauge32
      UNITS       "kilobits per second"
      MAX-ACCESS  read-only
      STATUS      current
      ::= { slapmPRMonEntry 9 }

   slapmPRMonMinRateLow OBJECT-TYPE
      SYNTAX      Unsigned32
      UNITS       "kilobits per second"
      MAX-ACCESS  read-create
      STATUS      current
      ::= { slapmPRMonEntry 10 }

   slapmPRMonMinRateHigh OBJECT-TYPE
      SYNTAX      Unsigned32
      UNITS       "kilobits per second"
      MAX-ACCESS  read-create
      STATUS      current
      ::= { slapmPRMonEntry 11 }

   slapmPRMonMaxRateHigh OBJECT-TYPE
      SYNTAX      Unsigned32
      UNITS       "kilobits per second"
      MAX-ACCESS  read-create
      STATUS      current
      ::= { slapmPRMonEntry 12 }

   slapmPRMonMaxRateLow OBJECT-TYPE
      SYNTAX      Unsigned32
      UNITS       "kilobits per second"
      MAX-ACCESS  read-create
      STATUS      current
      ::= { slapmPRMonEntry 13 }

   slapmPRMonMaxDelayHigh OBJECT-TYPE
      SYNTAX      Unsigned32
      UNITS       "milliseconds"
      MAX-ACCESS  read-create
      STATUS      current
      ::= { slapmPRMonEntry 14 }

   slapmPRMonMaxDelayLow OBJECT-TYPE
      SYNTAX      Unsigned32
      UNITS       "milliseconds"
      MAX-ACCESS  read-create
      STATUS      current
      ::= { slapmPRMonEntry 15 }

   slapmPRMonMinInRateNotAchieves OBJECT-TYPE
      SYNTAX      Counter32
      MAX-ACCESS  read-only
      STATUS      current
      ::= { slapmPRMonEntry 16 }

   slapmPRMonMaxInRateExceeds OBJECT-TYPE
      SYNTAX      Counter32
      MAX-ACCESS  read-only
      STATUS      current
      ::= { slapmPRMonEntry 17 }

   slapmPRMonMaxDelayExceeds OBJECT-TYPE





      SYNTAX      Counter32
      MAX-ACCESS  read-only
      STATUS      current
      ::= { slapmPRMonEntry 18 }

   slapmPRMonMinOutRateNotAchieves OBJECT-TYPE
      SYNTAX      Counter32
      MAX-ACCESS  read-only
      STATUS      current
      ::= { slapmPRMonEntry 19 }

   slapmPRMonMaxOutRateExceeds OBJECT-TYPE
      SYNTAX      Counter32
      MAX-ACCESS  read-only
      STATUS      current
      ::= { slapmPRMonEntry 20 }

   slapmPRMonCurrentDelayRate OBJECT-TYPE
      SYNTAX      Gauge32
      UNITS       "milliseconds"
      MAX-ACCESS  read-only
      STATUS      current
      ::= { slapmPRMonEntry 21 }

   slapmPRMonRowStatus  OBJECT-TYPE
      SYNTAX       RowStatus
      MAX-ACCESS   read-create
      STATUS       current
      ::= { slapmPRMonEntry 22 }


   slapmMonitoredEventNotAchieved NOTIFICATION-TYPE
      OBJECTS {
          slapmPolicyMonitorIntTime,
          slapmPolicyMonitorControl,
          slapmPolicyMonitorStatus,
          slapmPolicyMonitorStatus,
          slapmPolicyMonitorCurrentInRate,
          slapmPolicyMonitorCurrentOutRate,
          slapmPolicyMonitorCurrentDelayRate
      }
      STATUS  deprecated
      ::= { slapmNotifications 1 }

   slapmMonitoredEventOkay NOTIFICATION-TYPE
      OBJECTS {
          slapmPolicyMonitorIntTime,
          slapmPolicyMonitorControl,
          slapmPolicyMonitorStatus,
          slapmPolicyMonitorStatus,
          slapmPolicyMonitorCurrentInRate,
          slapmPolicyMonitorCurrentOutRate,





          slapmPolicyMonitorCurrentDelayRate
      }
      STATUS  deprecated
      ::= { slapmNotifications 2 }

   slapmPolicyProfileDeleted NOTIFICATION-TYPE
      OBJECTS {
          slapmPolicyStatsActiveConns,
          slapmPolicyStatsTotalConns,
          slapmPolicyStatsFirstActivated,
          slapmPolicyStatsLastMapping,
          slapmPolicyStatsInOctets,
          slapmPolicyStatsOutOctets,
          slapmPolicyStatsConnectionLimit,
          slapmPolicyStatsCountAccepts,
          slapmPolicyStatsCountDenies,
          slapmPolicyStatsInDiscards,
          slapmPolicyStatsOutDiscards,
          slapmPolicyStatsInPackets,
          slapmPolicyStatsOutPackets,
          slapmPolicyStatsInProfileOctets,
          slapmPolicyStatsOutProfileOctets,
          slapmPolicyStatsMinRate,
          slapmPolicyStatsMaxRate,
          slapmPolicyStatsMaxDelay
      }
      STATUS  deprecated
      ::= { slapmNotifications 3 }





   slapmPolicyMonitorDeleted NOTIFICATION-TYPE
      OBJECTS {
          slapmPolicyMonitorStatus,
          slapmPolicyMonitorInterval,
          slapmPolicyMonitorIntTime,
          slapmPolicyMonitorCurrentInRate,
          slapmPolicyMonitorCurrentOutRate,
          slapmPolicyMonitorCurrentDelayRate,
          slapmPolicyMonitorMinRateLow,
          slapmPolicyMonitorMinRateHigh,
          slapmPolicyMonitorMaxRateHigh,
          slapmPolicyMonitorMaxRateLow,
          slapmPolicyMonitorMaxDelayHigh,
          slapmPolicyMonitorMaxDelayLow,
          slapmPolicyMonitorMinInRateNotAchieves,
          slapmPolicyMonitorMaxInRateExceeds,
          slapmPolicyMonitorMaxDelayExceeds,
          slapmPolicyMonitorMinOutRateNotAchieves,
          slapmPolicyMonitorMaxOutRateExceeds
      }
      STATUS  deprecated
      ::= { slapmNotifications 4 }

   slapmSubcomponentMonitoredEventNotAchieved NOTIFICATION-TYPE
      OBJECTS {
          slapmSubcomponentSystemAddress,
          slapmSubcomponentPolicyName,
          slapmSubcomponentTrafficProfileName,
          slapmSubcomponentMonitorStatus,
          slapmSubcomponentMonitorStatus,
          slapmSubcomponentMonitorIntTime,
          slapmSubcomponentMonitorCurrentInRate,
          slapmSubcomponentMonitorCurrentOutRate,
          slapmSubcomponentTcpRoundTripTime
      }
      STATUS  deprecated
      ::= { slapmNotifications 5 }

   slapmSubcomponentMonitoredEventOkay NOTIFICATION-TYPE
      OBJECTS {
          slapmSubcomponentSystemAddress,
          slapmSubcomponentPolicyName,
          slapmSubcomponentTrafficProfileName,
          slapmSubcomponentMonitorStatus,
          slapmSubcomponentMonitorStatus,
          slapmSubcomponentMonitorIntTime,
          slapmSubcomponentMonitorCurrentInRate,
          slapmSubcomponentMonitorCurrentOutRate,
          slapmSubcomponentTcpRoundTripTime
      }
      STATUS  deprecated
      ::= { slapmNotifications 6 }

   slapmPolicyRuleMonNotOkay NOTIFICATION-TYPE
      OBJECTS {
          slapmPRMonIntTime,
          slapmPRMonControl,
          slapmPRMonStatus,
          slapmPRMonStatus,
          slapmPRMonCurrentInRate,
          slapmPRMonCurrentOutRate,
          slapmPRMonCurrentDelayRate
      }
      STATUS  current
      ::= { slapmNotifications 7 }

   slapmPolicyRuleMonOkay NOTIFICATION-TYPE
      OBJECTS {
          slapmPRMonIntTime,
          slapmPRMonControl,
          slapmPRMonStatus,
          slapmPRMonStatus,
          slapmPRMonCurrentInRate,
          slapmPRMonCurrentOutRate,
          slapmPRMonCurrentDelayRate
      }
      STATUS  current
      ::= { slapmNotifications 8 }

   slapmPolicyRuleDeleted NOTIFICATION-TYPE
      OBJECTS {
          slapmPolicyRuleStatsActiveConns,
          slapmPolicyRuleStatsTotalConns,
          slapmPolicyRuleStatsLActivated,
          slapmPolicyRuleStatsLastMapping,
          slapmPolicyRuleStatsInOctets,





          slapmPolicyRuleStatsOutOctets,
          slapmPolicyRuleStatsConnLimit,
          slapmPolicyRuleStatsCountAccepts,
          slapmPolicyRuleStatsCountDenies,
          slapmPolicyRuleStatsInDiscards,
          slapmPolicyRuleStatsOutDiscards,
          slapmPolicyRuleStatsInPackets,
          slapmPolicyRuleStatsOutPackets,
          slapmPolicyRuleStatsInProOctets,
          slapmPolicyRuleStatsOutProOctets,
          slapmPolicyRuleStatsMinRate,
          slapmPolicyRuleStatsMaxRate,
          slapmPolicyRuleStatsMaxDelay,
          slapmPolicyRuleStatsTotalRsvpFlows,
          slapmPolicyRuleStatsActRsvpFlows
      }
      STATUS  current
      ::= { slapmNotifications 9 }

   slapmPolicyRuleMonDeleted NOTIFICATION-TYPE
      OBJECTS {
          slapmPRMonControl,
          slapmPRMonStatus,
          slapmPRMonInterval,
          slapmPRMonIntTime,
          slapmPRMonCurrentInRate,
          slapmPRMonCurrentOutRate,
          slapmPRMonCurrentDelayRate,
          slapmPRMonMinRateLow,
          slapmPRMonMinRateHigh,
          slapmPRMonMaxRateHigh,
          slapmPRMonMaxRateLow,
          slapmPRMonMaxDelayHigh,
          slapmPRMonMaxDelayLow,
          slapmPRMonMinInRateNotAchieves,
          slapmPRMonMaxInRateExceeds,
          slapmPRMonMaxDelayExceeds,
          slapmPRMonMinOutRateNotAchieves,
          slapmPRMonMaxOutRateExceeds
      }
      STATUS  current
      ::= { slapmNotifications 10 }

   slapmSubcMonitorNotOkay NOTIFICATION-TYPE
      OBJECTS {
          slapmSubcomponentSystemAddress,
          slapmSubcomponentPolicyRuleIndex,
          slapmPRMonControl,
          slapmSubcomponentMonitorStatus,
          slapmSubcomponentMonitorStatus,
          slapmSubcomponentMonitorIntTime,
          slapmSubcomponentMonitorCurrentInRate,
          slapmSubcomponentMonitorCurrentOutRate,
          slapmSubcomponentTcpRoundTripTime
      }
      STATUS  current
      ::= { slapmNotifications 11 }

   slapmSubcMonitorOkay NOTIFICATION-TYPE
      OBJECTS {
          slapmSubcomponentSystemAddress,
          slapmSubcomponentPolicyRuleIndex,
          slapmPRMonControl,
          slapmSubcomponentMonitorStatus,
          slapmSubcomponentMonitorStatus,
          slapmSubcomponentMonitorIntTime,
          slapmSubcomponentMonitorCurrentInRate,
          slapmSubcomponentMonitorCurrentOutRate,
          slapmSubcomponentTcpRoundTripTime
      }

      STATUS  current
      ::= { slapmNotifications 12 }


   slapmCompliances OBJECT IDENTIFIER ::= { slapmConformance 1 }
   slapmGroups      OBJECT IDENTIFIER ::= { slapmConformance 2 }


   slapmCompliance MODULE-COMPLIANCE
      STATUS  current
      MODULE  -- this module
          MANDATORY-GROUPS {
                              slapmBaseGroup2,
                              slapmNotGroup2
                           }
          GROUP slapmEndSystemGroup2
          GROUP slapmEndSystemNotGroup2
          GROUP slapmBaseGroup
          GROUP slapmNotGroup
          GROUP slapmOptionalGroup





          GROUP slapmEndSystemGroup
          GROUP slapmEndSystemNotGroup
      ::= { slapmCompliances 1 }


   slapmBaseGroup OBJECT-GROUP
     OBJECTS {
               slapmSpinLock,
               slapmPolicyCountQueries,
               slapmPolicyCountAccesses,
               slapmPolicyCountSuccessAccesses,
               slapmPolicyCountNotFounds,
               slapmPolicyPurgeTime,
               slapmPolicyTrapEnable,
               slapmPolicyStatsOperStatus,
               slapmPolicyStatsActiveConns,
               slapmPolicyStatsFirstActivated,
               slapmPolicyStatsLastMapping,
               slapmPolicyStatsInOctets,
               slapmPolicyStatsOutOctets,
               slapmPolicyStatsConnectionLimit,
               slapmPolicyStatsTotalConns,
               slapmPolicyStatsCountAccepts,
               slapmPolicyStatsCountDenies,
               slapmPolicyStatsInDiscards,
               slapmPolicyStatsOutDiscards,
               slapmPolicyStatsInPackets,
               slapmPolicyStatsOutPackets,
               slapmPolicyStatsMinRate,
               slapmPolicyStatsMaxRate,
               slapmPolicyStatsMaxDelay,
               slapmPolicyMonitorControl,
               slapmPolicyMonitorStatus,
               slapmPolicyMonitorInterval,
               slapmPolicyMonitorIntTime,
               slapmPolicyMonitorCurrentInRate,
               slapmPolicyMonitorCurrentOutRate,





               slapmPolicyMonitorMinRateLow,
               slapmPolicyMonitorMinRateHigh,
               slapmPolicyMonitorMaxRateHigh,
               slapmPolicyMonitorMaxRateLow,
               slapmPolicyMonitorMaxDelayHigh,
               slapmPolicyMonitorMaxDelayLow,
               slapmPolicyMonitorMinInRateNotAchieves,
               slapmPolicyMonitorMaxInRateExceeds,
               slapmPolicyMonitorMaxDelayExceeds,
               slapmPolicyMonitorMinOutRateNotAchieves,
               slapmPolicyMonitorMaxOutRateExceeds,
               slapmPolicyMonitorCurrentDelayRate,
               slapmPolicyMonitorRowStatus
              }
    STATUS deprecated
    ::= { slapmGroups 1 }

   slapmOptionalGroup OBJECT-GROUP
     OBJECTS {
               slapmPolicyStatsInProfileOctets,
               slapmPolicyStatsOutProfileOctets
             }
    STATUS deprecated
    ::= { slapmGroups 2 }

   slapmEndSystemGroup OBJECT-GROUP
     OBJECTS {
               slapmPolicyTrapFilter,
               slapmSubcomponentProtocol,
               slapmSubcomponentSystemAddress,
               slapmSubcomponentPolicyName,
               slapmSubcomponentTrafficProfileName,
               slapmSubcomponentLastActivity,
               slapmSubcomponentInOctets,
               slapmSubcomponentOutOctets,
               slapmSubcomponentTcpOutBufferedOctets,
               slapmSubcomponentTcpInBufferedOctets,
               slapmSubcomponentTcpReXmts,
               slapmSubcomponentTcpRoundTripTime,
               slapmSubcomponentTcpRoundTripVariance,
               slapmSubcomponentInPdus,
               slapmSubcomponentOutPdus,





               slapmSubcomponentApplName,
               slapmSubcomponentMonitorStatus,
               slapmSubcomponentMonitorIntTime,
               slapmSubcomponentMonitorCurrentOutRate,
               slapmSubcomponentMonitorCurrentInRate
             }
     STATUS  deprecated
     ::= { slapmGroups 3 }

   slapmNotGroup NOTIFICATION-GROUP
     NOTIFICATIONS {
               slapmMonitoredEventNotAchieved,
               slapmMonitoredEventOkay,
               slapmPolicyProfileDeleted,
               slapmPolicyMonitorDeleted
             }
     STATUS  deprecated
     ::= { slapmGroups 4 }

   slapmEndSystemNotGroup NOTIFICATION-GROUP
     NOTIFICATIONS {
               slapmSubcomponentMonitoredEventNotAchieved,
               slapmSubcomponentMonitoredEventOkay
             }
     STATUS  deprecated
     ::= { slapmGroups 5 }

   slapmBaseGroup2 OBJECT-GROUP
     OBJECTS {
               slapmSpinLock,
               slapmPolicyCountQueries,
               slapmPolicyCountAccesses,
               slapmPolicyCountSuccessAccesses,
               slapmPolicyCountNotFounds,
               slapmPolicyPurgeTime,
               slapmPolicyTrapEnable,
               slapmPolicyNameOfRule,
               slapmPolicyRuleStatsOperStatus,
               slapmPolicyRuleStatsActiveConns,





               slapmPolicyRuleStatsTotalConns,
               slapmPolicyRuleStatsLActivated,
               slapmPolicyRuleStatsLastMapping,
               slapmPolicyRuleStatsInOctets,
               slapmPolicyRuleStatsOutOctets,
               slapmPolicyRuleStatsConnLimit,
               slapmPolicyRuleStatsCountAccepts,
               slapmPolicyRuleStatsCountDenies,
               slapmPolicyRuleStatsInDiscards,
               slapmPolicyRuleStatsOutDiscards,
               slapmPolicyRuleStatsInPackets,
               slapmPolicyRuleStatsOutPackets,
               slapmPolicyRuleStatsInProOctets,
               slapmPolicyRuleStatsOutProOctets,
               slapmPolicyRuleStatsMinRate,
               slapmPolicyRuleStatsMaxRate,
               slapmPolicyRuleStatsMaxDelay,
               slapmPolicyRuleStatsTotalRsvpFlows,
               slapmPolicyRuleStatsActRsvpFlows,
               slapmPRMonControl,
               slapmPRMonStatus,
               slapmPRMonInterval,
               slapmPRMonIntTime,
               slapmPRMonCurrentInRate,
               slapmPRMonCurrentOutRate,
               slapmPRMonMinRateLow,
               slapmPRMonMinRateHigh,
               slapmPRMonMaxRateHigh,
               slapmPRMonMaxRateLow,
               slapmPRMonMaxDelayHigh,
               slapmPRMonMaxDelayLow,
               slapmPRMonMinInRateNotAchieves,
               slapmPRMonMaxInRateExceeds,
               slapmPRMonMaxDelayExceeds,
               slapmPRMonMinOutRateNotAchieves,
               slapmPRMonMaxOutRateExceeds,
               slapmPRMonCurrentDelayRate,
               slapmPRMonRowStatus
              }
    STATUS current
    ::= { slapmGroups 6 }

   slapmEndSystemGroup2 OBJECT-GROUP
     OBJECTS {
               slapmPolicyTrapFilter,





               slapmSubcomponentProtocol,
               slapmSubcomponentSystemAddress,
               slapmSubcomponentLastActivity,
               slapmSubcomponentInOctets,
               slapmSubcomponentOutOctets,
               slapmSubcomponentTcpOutBufferedOctets,
               slapmSubcomponentTcpInBufferedOctets,
               slapmSubcomponentTcpReXmts,
               slapmSubcomponentTcpRoundTripTime,
               slapmSubcomponentTcpRoundTripVariance,
               slapmSubcomponentInPdus,
               slapmSubcomponentOutPdus,
               slapmSubcomponentApplName,
               slapmSubcomponentMonitorStatus,
               slapmSubcomponentMonitorIntTime,
               slapmSubcomponentMonitorCurrentOutRate,
               slapmSubcomponentMonitorCurrentInRate,
               slapmSubcomponentPolicyRuleIndex
             }
     STATUS  current
     ::= { slapmGroups 7 }

   slapmNotGroup2 NOTIFICATION-GROUP
     NOTIFICATIONS {
               slapmPolicyRuleMonNotOkay,
               slapmPolicyRuleMonOkay,
               slapmPolicyRuleDeleted,
               slapmPolicyRuleMonDeleted
             }
     STATUS  current
     ::= { slapmGroups 8 }

   slapmEndSystemNotGroup2 NOTIFICATION-GROUP
     NOTIFICATIONS {
               slapmSubcMonitorNotOkay,
               slapmSubcMonitorOkay
             }
     STATUS  current
     ::= { slapmGroups 9 }





END
