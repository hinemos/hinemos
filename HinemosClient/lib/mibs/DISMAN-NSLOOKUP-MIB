DISMAN-NSLOOKUP-MIB DEFINITIONS ::= BEGIN

   IMPORTS
       MODULE-IDENTITY, OBJECT-TYPE,
       Unsigned32, mib-2, Integer32
           FROM SNMPv2-SMI                  -- RFC2578
       RowStatus
           FROM SNMPv2-TC                   -- RFC2579
       MODULE-COMPLIANCE, OBJECT-GROUP
           FROM SNMPv2-CONF                 -- RFC2580
       SnmpAdminString
           FROM SNMP-FRAMEWORK-MIB          -- RFC3411
       InetAddressType, InetAddress
           FROM INET-ADDRESS-MIB;           -- RFC4001

    lookupMIB MODULE-IDENTITY
       LAST-UPDATED "200606130000Z"         -- 13 June 2006
       ORGANIZATION "IETF Distributed Management Working Group"




       ::= { mib-2 82 }


    lookupObjects        OBJECT IDENTIFIER ::= { lookupMIB 1 }
    lookupConformance    OBJECT IDENTIFIER ::= { lookupMIB 2 }


    lookupMaxConcurrentRequests OBJECT-TYPE





       SYNTAX      Unsigned32
       UNITS       "requests"
       MAX-ACCESS  read-write
       STATUS      current
       DEFVAL { 10 }
       ::= { lookupObjects 1 }

    lookupPurgeTime OBJECT-TYPE
       SYNTAX      Unsigned32 (0..86400)
       UNITS       "seconds"
       MAX-ACCESS  read-write
       STATUS      current
       DEFVAL { 900 }  -- 15 minutes as default
       ::= { lookupObjects 2 }


    lookupCtlTable OBJECT-TYPE
       SYNTAX      SEQUENCE OF LookupCtlEntry
       MAX-ACCESS  not-accessible
       STATUS      current





      ::= { lookupObjects 3 }

    lookupCtlEntry OBJECT-TYPE
       SYNTAX      LookupCtlEntry
       MAX-ACCESS  not-accessible
       STATUS      current
       INDEX {
                lookupCtlOwnerIndex,
                lookupCtlOperationName
             }
       ::= { lookupCtlTable 1 }

    LookupCtlEntry ::=
       SEQUENCE {
           lookupCtlOwnerIndex         SnmpAdminString,
           lookupCtlOperationName      SnmpAdminString,
           lookupCtlTargetAddressType  InetAddressType,
           lookupCtlTargetAddress      InetAddress,
           lookupCtlOperStatus         INTEGER,
           lookupCtlTime               Unsigned32,
           lookupCtlRc                 Integer32,
           lookupCtlRowStatus          RowStatus
       }

    lookupCtlOwnerIndex OBJECT-TYPE
       SYNTAX      SnmpAdminString (SIZE(0..32))
       MAX-ACCESS  not-accessible
       STATUS      current
       ::= { lookupCtlEntry 1 }

    lookupCtlOperationName OBJECT-TYPE
       SYNTAX      SnmpAdminString (SIZE(0..32))
       MAX-ACCESS  not-accessible
       STATUS      current
       ::= { lookupCtlEntry 2 }

    lookupCtlTargetAddressType OBJECT-TYPE
       SYNTAX      InetAddressType
       MAX-ACCESS  read-create
       STATUS      current

       DEFVAL { unknown }
       ::= { lookupCtlEntry 3 }






    lookupCtlTargetAddress OBJECT-TYPE
       SYNTAX      InetAddress
       MAX-ACCESS  read-create
       STATUS      current
       ::= { lookupCtlEntry 4 }

    lookupCtlOperStatus OBJECT-TYPE
       SYNTAX      INTEGER {
                      enabled(1),    -- operation is active
                      notStarted(2), -- operation has not started
                      completed(3)   -- operation is done
                   }
       MAX-ACCESS  read-only
       STATUS      current
       ::= { lookupCtlEntry 5 }

    lookupCtlTime OBJECT-TYPE
       SYNTAX      Unsigned32
       UNITS       "milliseconds"
       MAX-ACCESS  read-only
       STATUS      current
       ::= { lookupCtlEntry 6 }

    lookupCtlRc OBJECT-TYPE
       SYNTAX      Integer32
       MAX-ACCESS  read-only
       STATUS      current
       ::= { lookupCtlEntry 7 }

    lookupCtlRowStatus OBJECT-TYPE
       SYNTAX      RowStatus
       MAX-ACCESS  read-create
       STATUS      current
       ::= { lookupCtlEntry 8 }



    lookupResultsTable OBJECT-TYPE
       SYNTAX      SEQUENCE OF LookupResultsEntry
       MAX-ACCESS  not-accessible
       STATUS      current
      ::= { lookupObjects 4 }

    lookupResultsEntry OBJECT-TYPE
       SYNTAX      LookupResultsEntry
       MAX-ACCESS  not-accessible
       STATUS      current
       INDEX {
                lookupCtlOwnerIndex,
                lookupCtlOperationName,
                lookupResultsIndex
             }
       ::= { lookupResultsTable 1 }

    LookupResultsEntry ::=
       SEQUENCE {
           lookupResultsIndex        Unsigned32,
           lookupResultsAddressType  InetAddressType,
           lookupResultsAddress      InetAddress
        }

    lookupResultsIndex OBJECT-TYPE
       SYNTAX      Unsigned32 (1..'ffffffff'h)
       MAX-ACCESS  not-accessible
       STATUS      current
       ::= { lookupResultsEntry 1 }

    lookupResultsAddressType OBJECT-TYPE
       SYNTAX      InetAddressType
       MAX-ACCESS  read-only
       STATUS      current
       ::= { lookupResultsEntry 2 }

    lookupResultsAddress OBJECT-TYPE
       SYNTAX      InetAddress
       MAX-ACCESS  read-only
       STATUS      current

       ::= { lookupResultsEntry 3 }



    lookupCompliances OBJECT IDENTIFIER ::= { lookupConformance 1 }
    lookupGroups      OBJECT IDENTIFIER ::= { lookupConformance 2 }


    lookupCompliance MODULE-COMPLIANCE
       STATUS  current
       MODULE  -- this module
           MANDATORY-GROUPS { lookupGroup }

           OBJECT lookupMaxConcurrentRequests
           MIN-ACCESS  read-only

           OBJECT lookupPurgeTime
           MIN-ACCESS  read-only





       ::= { lookupCompliances 1 }

    lookupMinimumCompliance MODULE-COMPLIANCE
       STATUS  current
       MODULE  -- this module
           MANDATORY-GROUPS { lookupGroup }

           OBJECT lookupMaxConcurrentRequests
           MIN-ACCESS  read-only

           OBJECT lookupPurgeTime
           MIN-ACCESS  read-only

           OBJECT lookupCtlRowStatus
           MIN-ACCESS  read-only
       ::= { lookupCompliances 2 }


    lookupGroup OBJECT-GROUP
      OBJECTS {
                lookupMaxConcurrentRequests,
                lookupPurgeTime,
                lookupCtlOperStatus,
                lookupCtlTargetAddressType,
                lookupCtlTargetAddress,
                lookupCtlTime,
                lookupCtlRc,
                lookupCtlRowStatus,





                lookupResultsAddressType,
                lookupResultsAddress
              }
      STATUS  current
       ::= { lookupGroups 1 }

   END
