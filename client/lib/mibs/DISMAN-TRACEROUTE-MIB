DISMAN-TRACEROUTE-MIB DEFINITIONS ::= BEGIN

   IMPORTS
       MODULE-IDENTITY, OBJECT-TYPE, Integer32,
       Gauge32, Unsigned32, mib-2,
       NOTIFICATION-TYPE,
       OBJECT-IDENTITY
           FROM SNMPv2-SMI                  -- RFC2578
       RowStatus, StorageType,
       TruthValue, DateAndTime
           FROM SNMPv2-TC                   -- RFC2579
       MODULE-COMPLIANCE, OBJECT-GROUP,
       NOTIFICATION-GROUP
           FROM SNMPv2-CONF                 -- RFC2580
       SnmpAdminString
           FROM SNMP-FRAMEWORK-MIB          -- RFC3411
       InterfaceIndexOrZero                 -- RFC2863
           FROM IF-MIB
       InetAddressType, InetAddress
           FROM INET-ADDRESS-MIB            -- RFC4001
       OperationResponseStatus
           FROM DISMAN-PING-MIB;            -- RFC4560

    traceRouteMIB MODULE-IDENTITY
       LAST-UPDATED "200606130000Z"         -- 13 June 2006
       ORGANIZATION "IETF Distributed Management Working Group"







       ::= { mib-2 81 }


    traceRouteNotifications  OBJECT IDENTIFIER ::= { traceRouteMIB 0 }
    traceRouteObjects        OBJECT IDENTIFIER ::= { traceRouteMIB 1 }
    traceRouteConformance    OBJECT IDENTIFIER ::= { traceRouteMIB 2 }


    traceRouteImplementationTypeDomains OBJECT IDENTIFIER
    ::= { traceRouteMIB 3 }





    traceRouteUsingUdpProbes OBJECT-IDENTITY
       STATUS      current
       ::= { traceRouteImplementationTypeDomains 1 }



    traceRouteMaxConcurrentRequests OBJECT-TYPE
       SYNTAX      Unsigned32
       UNITS       "requests"
       MAX-ACCESS  read-write
       STATUS      current
       DEFVAL { 10 }
       ::= { traceRouteObjects 1 }



    traceRouteCtlTable OBJECT-TYPE
       SYNTAX      SEQUENCE OF TraceRouteCtlEntry
       MAX-ACCESS  not-accessible
       STATUS      current
      ::= { traceRouteObjects 2 }

    traceRouteCtlEntry OBJECT-TYPE
       SYNTAX      TraceRouteCtlEntry
       MAX-ACCESS  not-accessible
       STATUS      current
       INDEX {
               traceRouteCtlOwnerIndex,
               traceRouteCtlTestName
             }
       ::= { traceRouteCtlTable 1 }

    TraceRouteCtlEntry ::=
       SEQUENCE {
         traceRouteCtlOwnerIndex         SnmpAdminString,
         traceRouteCtlTestName           SnmpAdminString,
         traceRouteCtlTargetAddressType  InetAddressType,
         traceRouteCtlTargetAddress      InetAddress,
         traceRouteCtlByPassRouteTable   TruthValue,
         traceRouteCtlDataSize           Unsigned32,
         traceRouteCtlTimeOut            Unsigned32,
         traceRouteCtlProbesPerHop       Unsigned32,
         traceRouteCtlPort               Unsigned32,
         traceRouteCtlMaxTtl             Unsigned32,
         traceRouteCtlDSField            Unsigned32,
         traceRouteCtlSourceAddressType  InetAddressType,
         traceRouteCtlSourceAddress      InetAddress,
         traceRouteCtlIfIndex            InterfaceIndexOrZero,
         traceRouteCtlMiscOptions        SnmpAdminString,
         traceRouteCtlMaxFailures        Unsigned32,
         traceRouteCtlDontFragment       TruthValue,
         traceRouteCtlInitialTtl         Unsigned32,
         traceRouteCtlFrequency          Unsigned32,
         traceRouteCtlStorageType        StorageType,
         traceRouteCtlAdminStatus        INTEGER,
         traceRouteCtlDescr              SnmpAdminString,
         traceRouteCtlMaxRows            Unsigned32,
         traceRouteCtlTrapGeneration     BITS,
         traceRouteCtlCreateHopsEntries  TruthValue,
         traceRouteCtlType               OBJECT IDENTIFIER,
         traceRouteCtlRowStatus          RowStatus
       }

    traceRouteCtlOwnerIndex OBJECT-TYPE
       SYNTAX      SnmpAdminString (SIZE(0..32))





       MAX-ACCESS  not-accessible
       STATUS      current
       ::= { traceRouteCtlEntry 1 }

     traceRouteCtlTestName OBJECT-TYPE
       SYNTAX      SnmpAdminString (SIZE(0..32))
       MAX-ACCESS  not-accessible
       STATUS      current
       ::= { traceRouteCtlEntry 2 }

    traceRouteCtlTargetAddressType OBJECT-TYPE
       SYNTAX      InetAddressType
       MAX-ACCESS  read-create
       STATUS      current
       DEFVAL { unknown }
       ::= { traceRouteCtlEntry 3 }






    traceRouteCtlTargetAddress OBJECT-TYPE
       SYNTAX      InetAddress
       MAX-ACCESS  read-create
       STATUS      current
       ::= { traceRouteCtlEntry 4 }

    traceRouteCtlByPassRouteTable OBJECT-TYPE
       SYNTAX TruthValue
       MAX-ACCESS  read-create
       STATUS      current
       DEFVAL { false }
       ::= { traceRouteCtlEntry 5 }

    traceRouteCtlDataSize OBJECT-TYPE
       SYNTAX      Unsigned32 (0..65507)
       UNITS       "octets"
       MAX-ACCESS  read-create
       STATUS      current
       DEFVAL { 0 }
       ::= { traceRouteCtlEntry 6 }

    traceRouteCtlTimeOut OBJECT-TYPE
       SYNTAX      Unsigned32 (1..60)
       UNITS       "seconds"
       MAX-ACCESS  read-create
       STATUS      current
       DEFVAL { 3 }
       ::= { traceRouteCtlEntry 7 }

    traceRouteCtlProbesPerHop OBJECT-TYPE
       SYNTAX      Unsigned32 (1..10)
       UNITS       "probes"
       MAX-ACCESS  read-create
       STATUS      current
       DEFVAL { 3 }
       ::= { traceRouteCtlEntry 8 }

    traceRouteCtlPort OBJECT-TYPE
       SYNTAX      Unsigned32 (1..65535)
       UNITS       "UDP Port"
       MAX-ACCESS  read-create
       STATUS      current
       DEFVAL { 33434 }
       ::= { traceRouteCtlEntry 9 }

    traceRouteCtlMaxTtl OBJECT-TYPE
       SYNTAX      Unsigned32 (1..255)
       UNITS       "time-to-live value"





       MAX-ACCESS  read-create
       STATUS      current
       DEFVAL { 30 }
       ::= { traceRouteCtlEntry 10 }

    traceRouteCtlDSField OBJECT-TYPE
       SYNTAX      Unsigned32 (0..255)
       MAX-ACCESS  read-create
       STATUS      current

       DEFVAL { 0 }
       ::= { traceRouteCtlEntry 11 }

    traceRouteCtlSourceAddressType OBJECT-TYPE
       SYNTAX      InetAddressType
       MAX-ACCESS  read-create
       STATUS      current
       DEFVAL { unknown }
       ::= { traceRouteCtlEntry 12 }





    traceRouteCtlSourceAddress OBJECT-TYPE
       SYNTAX      InetAddress
       MAX-ACCESS  read-create
       STATUS      current
       DEFVAL { ''H }
       ::= { traceRouteCtlEntry 13 }

    traceRouteCtlIfIndex OBJECT-TYPE
       SYNTAX      InterfaceIndexOrZero
       MAX-ACCESS  read-create
       STATUS      current
       DEFVAL { 0 }
       ::= { traceRouteCtlEntry 14 }

    traceRouteCtlMiscOptions OBJECT-TYPE
       SYNTAX      SnmpAdminString
       MAX-ACCESS  read-create
       STATUS      current
       DEFVAL { ''H }
       ::= { traceRouteCtlEntry 15 }

    traceRouteCtlMaxFailures OBJECT-TYPE
       SYNTAX      Unsigned32 (0..255)
       UNITS       "timeouts"
       MAX-ACCESS  read-create
       STATUS      current
       DEFVAL { 5 }
       ::= { traceRouteCtlEntry 16 }

    traceRouteCtlDontFragment OBJECT-TYPE
       SYNTAX         TruthValue
       MAX-ACCESS     read-create
       STATUS         current
       DEFVAL  { false }
       ::= { traceRouteCtlEntry 17 }

    traceRouteCtlInitialTtl OBJECT-TYPE
       SYNTAX         Unsigned32 (1..255)
       MAX-ACCESS     read-create
       STATUS         current
       DEFVAL { 1 }
       ::= { traceRouteCtlEntry 18 }

    traceRouteCtlFrequency  OBJECT-TYPE
       SYNTAX      Unsigned32
       UNITS       "seconds"
       MAX-ACCESS  read-create
       STATUS      current
       DEFVAL { 0 }
       ::= { traceRouteCtlEntry 19 }

    traceRouteCtlStorageType OBJECT-TYPE
       SYNTAX      StorageType
       MAX-ACCESS  read-create
       STATUS      current
       DEFVAL { nonVolatile }
       ::= { traceRouteCtlEntry 20 }

    traceRouteCtlAdminStatus OBJECT-TYPE
       SYNTAX      INTEGER {

                             enabled(1), -- operation should be started
                             disabled(2) -- operation should be stopped
                           }
       MAX-ACCESS  read-create
       STATUS      current
        DEFVAL { disabled }
       ::= { traceRouteCtlEntry 21 }

    traceRouteCtlDescr OBJECT-TYPE
       SYNTAX      SnmpAdminString
       MAX-ACCESS  read-create
       STATUS      current
       DEFVAL { ''H }
       ::= { traceRouteCtlEntry 22 }





    traceRouteCtlMaxRows OBJECT-TYPE
       SYNTAX      Unsigned32
       UNITS       "rows"
       MAX-ACCESS  read-create
       STATUS      current
       DEFVAL      { 50 }
       ::= { traceRouteCtlEntry 23 }

    traceRouteCtlTrapGeneration OBJECT-TYPE
       SYNTAX      BITS {
                     pathChange(0),
                     testFailure(1),
                     testCompletion(2)
                   }
       MAX-ACCESS  read-create
       STATUS      current





       DEFVAL { { } }
       ::= { traceRouteCtlEntry 24 }

    traceRouteCtlCreateHopsEntries OBJECT-TYPE
       SYNTAX      TruthValue
       MAX-ACCESS  read-create
       STATUS      current
       DEFVAL { false }
       ::= { traceRouteCtlEntry 25 }

    traceRouteCtlType OBJECT-TYPE
       SYNTAX      OBJECT IDENTIFIER
       MAX-ACCESS  read-create
       STATUS      current
       DEFVAL { traceRouteUsingUdpProbes }
       ::= { traceRouteCtlEntry 26 }

    traceRouteCtlRowStatus OBJECT-TYPE
       SYNTAX      RowStatus
       MAX-ACCESS  read-create
       STATUS      current
       ::= { traceRouteCtlEntry 27 }



    traceRouteResultsTable OBJECT-TYPE
       SYNTAX      SEQUENCE OF TraceRouteResultsEntry
       MAX-ACCESS  not-accessible
       STATUS      current
      ::= { traceRouteObjects 3 }

    traceRouteResultsEntry OBJECT-TYPE
       SYNTAX      TraceRouteResultsEntry
       MAX-ACCESS  not-accessible
       STATUS      current
       INDEX {
               traceRouteCtlOwnerIndex,
               traceRouteCtlTestName
             }
       ::= { traceRouteResultsTable 1 }

    TraceRouteResultsEntry ::=
       SEQUENCE {
         traceRouteResultsOperStatus       INTEGER,
         traceRouteResultsCurHopCount      Gauge32,
         traceRouteResultsCurProbeCount    Gauge32,
         traceRouteResultsIpTgtAddrType    InetAddressType,
         traceRouteResultsIpTgtAddr        InetAddress,
         traceRouteResultsTestAttempts     Gauge32,
         traceRouteResultsTestSuccesses    Gauge32,
         traceRouteResultsLastGoodPath     DateAndTime
       }

    traceRouteResultsOperStatus OBJECT-TYPE
       SYNTAX      INTEGER {
                             enabled(1),  -- test is in progress
                             disabled(2), -- test has stopped
                             completed(3) -- test is completed
                           }
       MAX-ACCESS  read-only
       STATUS      current
       ::= { traceRouteResultsEntry 1 }

    traceRouteResultsCurHopCount OBJECT-TYPE





       SYNTAX      Gauge32
       UNITS       "hops"
       MAX-ACCESS  read-only
       STATUS      current
       ::= { traceRouteResultsEntry 2 }

    traceRouteResultsCurProbeCount OBJECT-TYPE
       SYNTAX      Gauge32
       UNITS       "probes"
       MAX-ACCESS  read-only
       STATUS      current
       ::= { traceRouteResultsEntry 3 }

    traceRouteResultsIpTgtAddrType OBJECT-TYPE
       SYNTAX      InetAddressType

       MAX-ACCESS  read-only
       STATUS      current
       ::= { traceRouteResultsEntry 4 }

    traceRouteResultsIpTgtAddr OBJECT-TYPE
       SYNTAX      InetAddress
       MAX-ACCESS  read-only
       STATUS      current
       ::= { traceRouteResultsEntry 5 }

    traceRouteResultsTestAttempts OBJECT-TYPE





       SYNTAX      Gauge32
       UNITS       "tests"
       MAX-ACCESS  read-only
       STATUS      current
       ::= { traceRouteResultsEntry 6 }

    traceRouteResultsTestSuccesses OBJECT-TYPE
       SYNTAX      Gauge32
       UNITS       "tests"
       MAX-ACCESS  read-only
       STATUS      current
       ::= { traceRouteResultsEntry 7 }

    traceRouteResultsLastGoodPath OBJECT-TYPE
       SYNTAX      DateAndTime
       MAX-ACCESS  read-only
       STATUS      current
       ::= { traceRouteResultsEntry 8 }


    traceRouteProbeHistoryTable OBJECT-TYPE
       SYNTAX      SEQUENCE OF TraceRouteProbeHistoryEntry
       MAX-ACCESS  not-accessible
       STATUS      current
      ::= { traceRouteObjects 4 }

    traceRouteProbeHistoryEntry OBJECT-TYPE
       SYNTAX      TraceRouteProbeHistoryEntry
       MAX-ACCESS  not-accessible
       STATUS      current
       INDEX {
                traceRouteCtlOwnerIndex,
                traceRouteCtlTestName,
                traceRouteProbeHistoryIndex,
                traceRouteProbeHistoryHopIndex,
                traceRouteProbeHistoryProbeIndex

             }
       ::= { traceRouteProbeHistoryTable 1 }

    TraceRouteProbeHistoryEntry ::=
       SEQUENCE {
         traceRouteProbeHistoryIndex         Unsigned32,
         traceRouteProbeHistoryHopIndex      Unsigned32,
         traceRouteProbeHistoryProbeIndex    Unsigned32,
         traceRouteProbeHistoryHAddrType     InetAddressType,
         traceRouteProbeHistoryHAddr         InetAddress,
         traceRouteProbeHistoryResponse      Unsigned32,
         traceRouteProbeHistoryStatus        OperationResponseStatus,
         traceRouteProbeHistoryLastRC        Integer32,
         traceRouteProbeHistoryTime          DateAndTime
       }

    traceRouteProbeHistoryIndex OBJECT-TYPE





       SYNTAX      Unsigned32 (1..'ffffffff'h)
       MAX-ACCESS  not-accessible
       STATUS      current
       ::= { traceRouteProbeHistoryEntry 1 }

    traceRouteProbeHistoryHopIndex OBJECT-TYPE
       SYNTAX      Unsigned32 (1..255)
       MAX-ACCESS  not-accessible
       STATUS      current
       ::= { traceRouteProbeHistoryEntry 2 }

    traceRouteProbeHistoryProbeIndex OBJECT-TYPE
       SYNTAX      Unsigned32 (1..10)
       MAX-ACCESS  not-accessible
       STATUS      current
       ::= { traceRouteProbeHistoryEntry 3 }

    traceRouteProbeHistoryHAddrType OBJECT-TYPE
       SYNTAX      InetAddressType
       MAX-ACCESS  read-only
       STATUS      current
       ::= { traceRouteProbeHistoryEntry 4 }






    traceRouteProbeHistoryHAddr OBJECT-TYPE
       SYNTAX      InetAddress
       MAX-ACCESS  read-only
       STATUS      current
       ::= { traceRouteProbeHistoryEntry 5 }

    traceRouteProbeHistoryResponse OBJECT-TYPE
       SYNTAX      Unsigned32
       UNITS       "milliseconds"
       MAX-ACCESS  read-only
       STATUS      current
       ::= { traceRouteProbeHistoryEntry 6 }

    traceRouteProbeHistoryStatus OBJECT-TYPE
       SYNTAX      OperationResponseStatus
       MAX-ACCESS  read-only
       STATUS      current
       ::= { traceRouteProbeHistoryEntry 7 }

    traceRouteProbeHistoryLastRC OBJECT-TYPE
       SYNTAX      Integer32
       MAX-ACCESS  read-only

       STATUS      current
       ::= { traceRouteProbeHistoryEntry 8 }





    traceRouteProbeHistoryTime OBJECT-TYPE
       SYNTAX      DateAndTime
       MAX-ACCESS  read-only
       STATUS      current
       ::= { traceRouteProbeHistoryEntry 9 }


    traceRouteHopsTable OBJECT-TYPE
       SYNTAX      SEQUENCE OF TraceRouteHopsEntry
       MAX-ACCESS  not-accessible
       STATUS      current
       ::= { traceRouteObjects 5 }

    traceRouteHopsEntry OBJECT-TYPE
       SYNTAX      TraceRouteHopsEntry
       MAX-ACCESS  not-accessible
       STATUS      current
       INDEX {
               traceRouteCtlOwnerIndex,
               traceRouteCtlTestName,
               traceRouteHopsHopIndex
             }

       ::= { traceRouteHopsTable 1 }

    TraceRouteHopsEntry ::=
       SEQUENCE {
           traceRouteHopsHopIndex         Unsigned32,
           traceRouteHopsIpTgtAddressType InetAddressType,
           traceRouteHopsIpTgtAddress     InetAddress,
           traceRouteHopsMinRtt           Unsigned32,
           traceRouteHopsMaxRtt           Unsigned32,
           traceRouteHopsAverageRtt       Unsigned32,
           traceRouteHopsRttSumOfSquares  Unsigned32,





           traceRouteHopsSentProbes       Unsigned32,
           traceRouteHopsProbeResponses   Unsigned32,
           traceRouteHopsLastGoodProbe    DateAndTime
         }

    traceRouteHopsHopIndex OBJECT-TYPE
       SYNTAX      Unsigned32 (1..'ffffffff'h)
       MAX-ACCESS  not-accessible
       STATUS      current
       ::= { traceRouteHopsEntry 1 }

    traceRouteHopsIpTgtAddressType OBJECT-TYPE
       SYNTAX      InetAddressType
       MAX-ACCESS  read-only
       STATUS      current
       ::= { traceRouteHopsEntry 2 }

    traceRouteHopsIpTgtAddress OBJECT-TYPE
       SYNTAX      InetAddress
       MAX-ACCESS  read-only
       STATUS      current
       ::= { traceRouteHopsEntry 3 }

    traceRouteHopsMinRtt OBJECT-TYPE
       SYNTAX      Unsigned32
       MAX-ACCESS  read-only
       STATUS      current
       ::= { traceRouteHopsEntry 4 }

    traceRouteHopsMaxRtt OBJECT-TYPE
       SYNTAX      Unsigned32
       MAX-ACCESS  read-only
       STATUS      current
       ::= { traceRouteHopsEntry 5 }

    traceRouteHopsAverageRtt OBJECT-TYPE
       SYNTAX      Unsigned32
       MAX-ACCESS  read-only
       STATUS      current
       ::= { traceRouteHopsEntry 6 }

    traceRouteHopsRttSumOfSquares OBJECT-TYPE
       SYNTAX      Unsigned32
       MAX-ACCESS  read-only
       STATUS      current
       ::= { traceRouteHopsEntry 7 }

    traceRouteHopsSentProbes OBJECT-TYPE





       SYNTAX      Unsigned32
       MAX-ACCESS  read-only
       STATUS      current
       ::= { traceRouteHopsEntry 8 }

    traceRouteHopsProbeResponses OBJECT-TYPE
       SYNTAX      Unsigned32
       MAX-ACCESS  read-only
       STATUS      current
       ::= { traceRouteHopsEntry 9 }

    traceRouteHopsLastGoodProbe OBJECT-TYPE
       SYNTAX      DateAndTime
       MAX-ACCESS  read-only
       STATUS      current
       ::= { traceRouteHopsEntry 10 }


    traceRoutePathChange NOTIFICATION-TYPE
         OBJECTS {
           traceRouteCtlTargetAddressType,
           traceRouteCtlTargetAddress,
           traceRouteResultsIpTgtAddrType,
           traceRouteResultsIpTgtAddr
         }
         STATUS  current
         ::= { traceRouteNotifications 1 }

    traceRouteTestFailed NOTIFICATION-TYPE
         OBJECTS {
           traceRouteCtlTargetAddressType,
           traceRouteCtlTargetAddress,
           traceRouteResultsIpTgtAddrType,
           traceRouteResultsIpTgtAddr





         }
         STATUS  current
         ::= { traceRouteNotifications 2 }

    traceRouteTestCompleted NOTIFICATION-TYPE
         OBJECTS {
           traceRouteCtlTargetAddressType,
           traceRouteCtlTargetAddress,
           traceRouteResultsIpTgtAddrType,
           traceRouteResultsIpTgtAddr
         }
         STATUS  current
         ::= { traceRouteNotifications 3 }


    traceRouteCompliances OBJECT IDENTIFIER
         ::= { traceRouteConformance 1 }
    traceRouteGroups      OBJECT IDENTIFIER
         ::= { traceRouteConformance 2 }


    traceRouteFullCompliance MODULE-COMPLIANCE
       STATUS  current
       MODULE  -- this module
           MANDATORY-GROUPS {
                               traceRouteMinimumGroup,
                               traceRouteCtlRowStatusGroup,
                               traceRouteHistoryGroup
                            }

           GROUP traceRouteHopsTableGroup

           GROUP traceRouteNotificationsGroup

           OBJECT traceRouteMaxConcurrentRequests
           MIN-ACCESS  read-only

           OBJECT traceRouteCtlByPassRouteTable
           MIN-ACCESS  read-only

           OBJECT traceRouteCtlDSField
           MIN-ACCESS  read-only

           OBJECT traceRouteCtlSourceAddressType
           SYNTAX  InetAddressType { unknown(0), ipv4(1), ipv6(2) }
           MIN-ACCESS  read-only

           OBJECT traceRouteCtlSourceAddress
           SYNTAX  InetAddress (SIZE(0|4|16))
           MIN-ACCESS  read-only

           OBJECT traceRouteCtlIfIndex
           MIN-ACCESS  read-only

           OBJECT traceRouteCtlMiscOptions
           MIN-ACCESS  read-only

           OBJECT traceRouteCtlStorageType
           MIN-ACCESS  read-only

           OBJECT traceRouteCtlType
           MIN-ACCESS  read-only

           OBJECT traceRouteResultsIpTgtAddrType
           SYNTAX  InetAddressType { unknown(0), ipv4(1), ipv6(2) }

           OBJECT traceRouteResultsIpTgtAddr
           SYNTAX  InetAddress (SIZE(0|4|16))

           OBJECT traceRouteResultsLastGoodPath

           OBJECT traceRouteProbeHistoryHAddrType
           SYNTAX  InetAddressType { unknown(0), ipv4(1), ipv6(2) }






           OBJECT traceRouteProbeHistoryHAddr
           SYNTAX  InetAddress (SIZE(0|4|16))

           OBJECT traceRouteProbeHistoryTime

           OBJECT traceRouteHopsIpTgtAddressType
           SYNTAX  InetAddressType { unknown(0), ipv4(1), ipv6(2) }

           OBJECT traceRouteHopsIpTgtAddress
           SYNTAX  InetAddress (SIZE(0|4|16))

           OBJECT traceRouteHopsLastGoodProbe

       ::= { traceRouteCompliances 2 }

    traceRouteMinimumCompliance MODULE-COMPLIANCE
       STATUS  current
       MODULE  -- this module





           MANDATORY-GROUPS { traceRouteMinimumGroup }

           GROUP traceRouteCtlRowStatusGroup

           GROUP traceRouteHistoryGroup

           GROUP traceRouteHopsTableGroup

           GROUP traceRouteNotificationsGroup

           OBJECT traceRouteMaxConcurrentRequests
           MIN-ACCESS  read-only

           OBJECT traceRouteCtlByPassRouteTable
           MIN-ACCESS  read-only

           OBJECT traceRouteCtlDSField
           MIN-ACCESS  read-only

           OBJECT traceRouteCtlSourceAddressType
           SYNTAX  InetAddressType { unknown(0), ipv4(1), ipv6(2) }
           MIN-ACCESS  read-only






           OBJECT traceRouteCtlSourceAddress
           SYNTAX  InetAddress (SIZE(0|4|16))
           MIN-ACCESS  read-only


           OBJECT traceRouteCtlIfIndex
           MIN-ACCESS  read-only

           OBJECT traceRouteCtlMiscOptions
           MIN-ACCESS  read-only

           OBJECT traceRouteCtlDontFragment
           MIN-ACCESS  read-only

           OBJECT traceRouteCtlInitialTtl
           MIN-ACCESS  read-only

           OBJECT traceRouteCtlFrequency
           MIN-ACCESS  read-only

           OBJECT traceRouteCtlStorageType
           MIN-ACCESS  read-only

           OBJECT traceRouteCtlDescr
           MIN-ACCESS  read-only

           OBJECT traceRouteCtlMaxRows
           MIN-ACCESS  read-only

           OBJECT traceRouteCtlTrapGeneration
           MIN-ACCESS  read-only

           OBJECT traceRouteCtlCreateHopsEntries
           MIN-ACCESS  read-only

           OBJECT traceRouteCtlType
           MIN-ACCESS  read-only

           OBJECT traceRouteResultsIpTgtAddrType
           SYNTAX  InetAddressType { unknown(0), ipv4(1), ipv6(2) }

           OBJECT traceRouteResultsIpTgtAddr
           SYNTAX  InetAddress (SIZE(0|4|16))

           OBJECT traceRouteResultsLastGoodPath

           OBJECT traceRouteProbeHistoryHAddrType
           SYNTAX  InetAddressType { unknown(0), ipv4(1), ipv6(2) }

           OBJECT traceRouteProbeHistoryHAddr
           SYNTAX  InetAddress (SIZE(0|4|16))

           OBJECT traceRouteProbeHistoryTime

           OBJECT traceRouteHopsIpTgtAddressType
           SYNTAX  InetAddressType { unknown(0), ipv4(1), ipv6(2) }

           OBJECT traceRouteHopsIpTgtAddress
           SYNTAX  InetAddress (SIZE(0|4|16))

           OBJECT traceRouteHopsLastGoodProbe

       ::= { traceRouteCompliances 3 }

    traceRouteCompliance MODULE-COMPLIANCE
       STATUS  deprecated
       MODULE  -- this module
           MANDATORY-GROUPS {
                               traceRouteGroup
                             }
           GROUP traceRouteTimeStampGroup

           GROUP traceRouteNotificationsGroup

           GROUP traceRouteHopsTableGroup





           OBJECT traceRouteMaxConcurrentRequests
           MIN-ACCESS  read-only

           OBJECT traceRouteCtlByPassRouteTable
           MIN-ACCESS  read-only

           OBJECT traceRouteCtlSourceAddressType
           SYNTAX  InetAddressType { unknown(0), ipv4(1), ipv6(2) }
           MIN-ACCESS  read-only


           OBJECT traceRouteCtlSourceAddress
           SYNTAX  InetAddress (SIZE(0|4|16))
           MIN-ACCESS  read-only

           OBJECT traceRouteCtlIfIndex
           MIN-ACCESS  read-only

           OBJECT traceRouteCtlMiscOptions
           MIN-ACCESS  read-only





           OBJECT traceRouteCtlStorageType
           MIN-ACCESS  read-only

           OBJECT traceRouteCtlDSField
           MIN-ACCESS  read-only

           OBJECT traceRouteCtlType
           MIN-ACCESS  read-only

           OBJECT traceRouteResultsIpTgtAddrType
           SYNTAX  InetAddressType { unknown(0), ipv4(1), ipv6(2) }

           OBJECT traceRouteResultsIpTgtAddr
           SYNTAX  InetAddress (SIZE(0|4|16))

           OBJECT traceRouteProbeHistoryHAddrType
           SYNTAX  InetAddressType { unknown(0), ipv4(1), ipv6(2) }

           OBJECT traceRouteProbeHistoryHAddr
           SYNTAX  InetAddress (SIZE(0|4|16))

           OBJECT traceRouteHopsIpTgtAddressType
           SYNTAX  InetAddressType { unknown(0), ipv4(1), ipv6(2) }






           OBJECT traceRouteHopsIpTgtAddress
           SYNTAX  InetAddress (SIZE(0|4|16))
       ::= { traceRouteCompliances 1 }


    traceRouteMinimumGroup OBJECT-GROUP
      OBJECTS {
                traceRouteMaxConcurrentRequests,
                traceRouteCtlTargetAddressType,
                traceRouteCtlTargetAddress,
                traceRouteCtlByPassRouteTable,
                traceRouteCtlDataSize,
                traceRouteCtlTimeOut,
                traceRouteCtlProbesPerHop,
                traceRouteCtlPort,
                traceRouteCtlMaxTtl,
                traceRouteCtlDSField,
                traceRouteCtlSourceAddressType,
                traceRouteCtlSourceAddress,
                traceRouteCtlIfIndex,
                traceRouteCtlMiscOptions,
                traceRouteCtlMaxFailures,
                traceRouteCtlDontFragment,
                traceRouteCtlInitialTtl,
                traceRouteCtlFrequency,
                traceRouteCtlStorageType,
                traceRouteCtlAdminStatus,
                traceRouteCtlMaxRows,
                traceRouteCtlTrapGeneration,
                traceRouteCtlDescr,
                traceRouteCtlCreateHopsEntries,
                traceRouteCtlType,
                traceRouteResultsOperStatus,
                traceRouteResultsCurHopCount,
                traceRouteResultsCurProbeCount,
                traceRouteResultsIpTgtAddrType,
                traceRouteResultsIpTgtAddr,
                traceRouteResultsTestAttempts,
                traceRouteResultsTestSuccesses,
                traceRouteResultsLastGoodPath





             }
      STATUS  current
      ::= { traceRouteGroups 5 }

    traceRouteCtlRowStatusGroup OBJECT-GROUP
      OBJECTS {
                traceRouteCtlRowStatus
             }
      STATUS  current
      ::= { traceRouteGroups 6 }

    traceRouteHistoryGroup OBJECT-GROUP
      OBJECTS {
                traceRouteProbeHistoryHAddrType,
                traceRouteProbeHistoryHAddr,
                traceRouteProbeHistoryResponse,
                traceRouteProbeHistoryStatus,
                traceRouteProbeHistoryLastRC,
                traceRouteProbeHistoryTime
              }

      STATUS  current
       ::= { traceRouteGroups 7 }

    traceRouteNotificationsGroup NOTIFICATION-GROUP
      NOTIFICATIONS {
                traceRoutePathChange,
                traceRouteTestFailed,
                traceRouteTestCompleted
             }
      STATUS   current
      ::= { traceRouteGroups 3 }

    traceRouteHopsTableGroup OBJECT-GROUP
      OBJECTS {
                traceRouteHopsIpTgtAddressType,
                traceRouteHopsIpTgtAddress,





                traceRouteHopsMinRtt,
                traceRouteHopsMaxRtt,
                traceRouteHopsAverageRtt,
                traceRouteHopsRttSumOfSquares,
                traceRouteHopsSentProbes,
                traceRouteHopsProbeResponses,
                traceRouteHopsLastGoodProbe
              }
       STATUS   current
     ::= { traceRouteGroups 4 }

    traceRouteGroup OBJECT-GROUP
      OBJECTS {
                traceRouteMaxConcurrentRequests,
                traceRouteCtlTargetAddressType,
                traceRouteCtlTargetAddress,
                traceRouteCtlByPassRouteTable,
                traceRouteCtlDataSize,
                traceRouteCtlTimeOut,
                traceRouteCtlProbesPerHop,
                traceRouteCtlPort,
                traceRouteCtlMaxTtl,
                traceRouteCtlDSField,
                traceRouteCtlSourceAddressType,
                traceRouteCtlSourceAddress,
                traceRouteCtlIfIndex,
                traceRouteCtlMiscOptions,
                traceRouteCtlMaxFailures,
                traceRouteCtlDontFragment,
                traceRouteCtlInitialTtl,
                traceRouteCtlFrequency,
                traceRouteCtlStorageType,
                traceRouteCtlAdminStatus,
                traceRouteCtlMaxRows,
                traceRouteCtlTrapGeneration,
                traceRouteCtlDescr,
                traceRouteCtlCreateHopsEntries,
                traceRouteCtlType,
                traceRouteCtlRowStatus,
                traceRouteResultsOperStatus,
                traceRouteResultsCurHopCount,
                traceRouteResultsCurProbeCount,
                traceRouteResultsIpTgtAddrType,
                traceRouteResultsIpTgtAddr,
                traceRouteResultsTestAttempts,





                traceRouteResultsTestSuccesses,
                traceRouteProbeHistoryHAddrType,
                traceRouteProbeHistoryHAddr,
                traceRouteProbeHistoryResponse,
                traceRouteProbeHistoryStatus,
                traceRouteProbeHistoryLastRC
             }
      STATUS  deprecated
      ::= { traceRouteGroups 1 }

    traceRouteTimeStampGroup OBJECT-GROUP
      OBJECTS {
                traceRouteResultsLastGoodPath,
                traceRouteProbeHistoryTime
              }
      STATUS  deprecated
       ::= { traceRouteGroups 2 }

   END
