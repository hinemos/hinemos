EFM-CU-MIB DEFINITIONS ::= BEGIN

     IMPORTS
       MODULE-IDENTITY, OBJECT-TYPE, NOTIFICATION-TYPE, Integer32,
       Unsigned32, Counter32, mib-2
         FROM SNMPv2-SMI         -- [RFC2578]
       TEXTUAL-CONVENTION, TruthValue, RowStatus, PhysAddress
         FROM SNMPv2-TC          -- [RFC2579]
       MODULE-COMPLIANCE, OBJECT-GROUP, NOTIFICATION-GROUP
         FROM SNMPv2-CONF        -- [RFC2580]
       SnmpAdminString
         FROM SNMP-FRAMEWORK-MIB -- [RFC3411]
       ifIndex, ifSpeed
         FROM IF-MIB             -- [RFC2863]
       ;

     efmCuMIB MODULE-IDENTITY
       LAST-UPDATED "200711140000Z"  -- November 14, 2007
       ORGANIZATION "IETF Ethernet Interfaces and Hub MIB Working Group"








       ::= { mib-2 167 }


      efmCuObjects     OBJECT IDENTIFIER ::= { efmCuMIB 1 }

      efmCuConformance OBJECT IDENTIFIER ::= { efmCuMIB 2 }


      efmCuPort        OBJECT IDENTIFIER ::= { efmCuObjects 1 }

      efmCuPme         OBJECT IDENTIFIER ::= { efmCuObjects 2 }


      EfmProfileIndex ::= TEXTUAL-CONVENTION
        DISPLAY-HINT "d"
        STATUS       current
        SYNTAX       Unsigned32 (1..255)

      EfmProfileIndexOrZero ::= TEXTUAL-CONVENTION
        DISPLAY-HINT "d"
        STATUS       current
        SYNTAX       Unsigned32 (0..255)

      EfmProfileIndexList ::= TEXTUAL-CONVENTION
        DISPLAY-HINT "1d:"





        STATUS       current
        SYNTAX       OCTET STRING (SIZE(0..6))

      EfmTruthValueOrUnknown ::= TEXTUAL-CONVENTION
        STATUS       current
        SYNTAX       INTEGER { unknown(0), true(1), false(2) }


      efmCuPortNotifications OBJECT IDENTIFIER ::= { efmCuPort 0 }

      efmCuLowRateCrossing NOTIFICATION-TYPE
        OBJECTS {
          ifSpeed,
          efmCuThreshLowRate
        }
        STATUS      current
        ::= { efmCuPortNotifications 1 }


      efmCuPortConfTable OBJECT-TYPE
        SYNTAX      SEQUENCE OF EfmCuPortConfEntry
        MAX-ACCESS  not-accessible
        STATUS      current
        ::= { efmCuPort 1 }

      efmCuPortConfEntry OBJECT-TYPE
        SYNTAX      EfmCuPortConfEntry
        MAX-ACCESS  not-accessible
        STATUS      current
        INDEX  { ifIndex }
        ::= { efmCuPortConfTable 1 }

      EfmCuPortConfEntry ::=
        SEQUENCE {
          efmCuPAFAdminState               INTEGER,





          efmCuPAFDiscoveryCode            PhysAddress,
          efmCuAdminProfile                EfmProfileIndexList,
          efmCuTargetDataRate              Unsigned32,
          efmCuTargetSnrMgn                Unsigned32,
          efmCuAdaptiveSpectra             TruthValue,
          efmCuThreshLowRate               Unsigned32,
          efmCuLowRateCrossingEnable       TruthValue
        }

      efmCuPAFAdminState  OBJECT-TYPE
        SYNTAX      INTEGER {
          enabled(1),
          disabled(2)
        }
        MAX-ACCESS  read-write
        STATUS      current
        ::= { efmCuPortConfEntry 1 }





      efmCuPAFDiscoveryCode  OBJECT-TYPE
        SYNTAX      PhysAddress (SIZE(0|6))
        MAX-ACCESS  read-write
        STATUS      current
        ::= { efmCuPortConfEntry 2 }

      efmCuAdminProfile  OBJECT-TYPE
        SYNTAX      EfmProfileIndexList
        MAX-ACCESS  read-write
        STATUS      current
        DEFVAL { '01'H }
        ::= { efmCuPortConfEntry 3 }

      efmCuTargetDataRate  OBJECT-TYPE
        SYNTAX      Unsigned32(1..100000|999999)
        UNITS       "Kbps"
        MAX-ACCESS  read-write
        STATUS      current
        ::= { efmCuPortConfEntry 4 }

      efmCuTargetSnrMgn  OBJECT-TYPE
        SYNTAX      Unsigned32(0..21)
        UNITS       "dB"
        MAX-ACCESS  read-write
        STATUS      current
        ::= { efmCuPortConfEntry 5 }

      efmCuAdaptiveSpectra  OBJECT-TYPE
        SYNTAX      TruthValue
        MAX-ACCESS  read-write
        STATUS      current
        ::= { efmCuPortConfEntry 6 }

      efmCuThreshLowRate  OBJECT-TYPE
        SYNTAX      Unsigned32(1..100000)
        UNITS       "Kbps"
        MAX-ACCESS  read-write
        STATUS      current
        ::= { efmCuPortConfEntry 7 }

      efmCuLowRateCrossingEnable  OBJECT-TYPE
        SYNTAX      TruthValue
        MAX-ACCESS  read-write
        STATUS      current
        ::= { efmCuPortConfEntry 8 }


      efmCuPortCapabilityTable OBJECT-TYPE
        SYNTAX      SEQUENCE OF EfmCuPortCapabilityEntry
        MAX-ACCESS  not-accessible
        STATUS      current





        ::= { efmCuPort 2 }

      efmCuPortCapabilityEntry OBJECT-TYPE
        SYNTAX      EfmCuPortCapabilityEntry
        MAX-ACCESS  not-accessible
        STATUS      current
        INDEX  { ifIndex }
        ::= { efmCuPortCapabilityTable 1 }

      EfmCuPortCapabilityEntry ::=
        SEQUENCE {
          efmCuPAFSupported                TruthValue,
          efmCuPeerPAFSupported            EfmTruthValueOrUnknown,
          efmCuPAFCapacity                 Unsigned32,
          efmCuPeerPAFCapacity             Unsigned32
        }

      efmCuPAFSupported  OBJECT-TYPE
        SYNTAX      TruthValue
        MAX-ACCESS  read-only
        STATUS      current
        ::= { efmCuPortCapabilityEntry 1 }

      efmCuPeerPAFSupported  OBJECT-TYPE
        SYNTAX      EfmTruthValueOrUnknown





        MAX-ACCESS  read-only
        STATUS      current
        ::= { efmCuPortCapabilityEntry 2 }

      efmCuPAFCapacity  OBJECT-TYPE
        SYNTAX      Unsigned32 (1..32)
        MAX-ACCESS  read-only
        STATUS      current
        ::= { efmCuPortCapabilityEntry 3 }

      efmCuPeerPAFCapacity  OBJECT-TYPE
        SYNTAX      Unsigned32 (0|1..32)
        MAX-ACCESS  read-only
        STATUS      current
        ::= { efmCuPortCapabilityEntry 4 }

      efmCuPortStatusTable OBJECT-TYPE
        SYNTAX      SEQUENCE OF EfmCuPortStatusEntry
        MAX-ACCESS  not-accessible
        STATUS      current
        ::= { efmCuPort 3 }

      efmCuPortStatusEntry OBJECT-TYPE
        SYNTAX      EfmCuPortStatusEntry
        MAX-ACCESS  not-accessible
        STATUS      current
        INDEX  { ifIndex }
        ::= { efmCuPortStatusTable 1 }

      EfmCuPortStatusEntry ::=
        SEQUENCE {
          efmCuFltStatus                   BITS,
          efmCuPortSide                    INTEGER,
          efmCuNumPMEs                     Unsigned32,
          efmCuPAFInErrors                 Counter32,
          efmCuPAFInSmallFragments         Counter32,
          efmCuPAFInLargeFragments         Counter32,
          efmCuPAFInBadFragments           Counter32,
          efmCuPAFInLostFragments          Counter32,
          efmCuPAFInLostStarts             Counter32,
          efmCuPAFInLostEnds               Counter32,
          efmCuPAFInOverflows              Counter32
        }






      efmCuFltStatus  OBJECT-TYPE
        SYNTAX      BITS {
          noPeer(0),
          peerPowerLoss(1),
          pmeSubTypeMismatch(2),
          lowRate(3)
        }
        MAX-ACCESS  read-only
        STATUS      current
        ::= { efmCuPortStatusEntry 1 }

      efmCuPortSide  OBJECT-TYPE
        SYNTAX      INTEGER {
          subscriber(1),
          office(2),
          unknown(3)
        }
        MAX-ACCESS  read-only
        STATUS      current
        ::= { efmCuPortStatusEntry 2 }

      efmCuNumPMEs  OBJECT-TYPE
        SYNTAX      Unsigned32 (0..32)
        MAX-ACCESS  read-only
        STATUS      current
        ::= { efmCuPortStatusEntry 3 }

      efmCuPAFInErrors OBJECT-TYPE
        SYNTAX      Counter32
        MAX-ACCESS  read-only
        STATUS      current
        ::= { efmCuPortStatusEntry 4 }

      efmCuPAFInSmallFragments OBJECT-TYPE
        SYNTAX      Counter32
        MAX-ACCESS  read-only
        STATUS      current
        ::= { efmCuPortStatusEntry 5 }

      efmCuPAFInLargeFragments OBJECT-TYPE
        SYNTAX      Counter32
        MAX-ACCESS  read-only
        STATUS      current
        ::= { efmCuPortStatusEntry 6 }

      efmCuPAFInBadFragments OBJECT-TYPE
        SYNTAX      Counter32
        MAX-ACCESS  read-only
        STATUS      current
        ::= { efmCuPortStatusEntry 7 }

      efmCuPAFInLostFragments OBJECT-TYPE
        SYNTAX      Counter32
        MAX-ACCESS  read-only
        STATUS      current
        ::= { efmCuPortStatusEntry 8 }

      efmCuPAFInLostStarts OBJECT-TYPE
        SYNTAX      Counter32
        MAX-ACCESS  read-only
        STATUS      current
        ::= { efmCuPortStatusEntry 9 }

      efmCuPAFInLostEnds OBJECT-TYPE
        SYNTAX      Counter32
        MAX-ACCESS  read-only
        STATUS      current
        ::= { efmCuPortStatusEntry 10 }





      efmCuPAFInOverflows OBJECT-TYPE
        SYNTAX      Counter32
        MAX-ACCESS  read-only
        STATUS      current
        ::= { efmCuPortStatusEntry 11 }


      efmCuPmeNotifications OBJECT IDENTIFIER ::= { efmCuPme 0 }

      efmCuPmeLineAtnCrossing NOTIFICATION-TYPE
        OBJECTS {
          efmCuPmeLineAtn,
          efmCuPmeThreshLineAtn
        }
        STATUS      current





        ::= { efmCuPmeNotifications 1 }

      efmCuPmeSnrMgnCrossing NOTIFICATION-TYPE
        OBJECTS {
          efmCuPmeSnrMgn,
          efmCuPmeThreshSnrMgn
        }
        STATUS      current
        ::= { efmCuPmeNotifications 2 }

      efmCuPmeDeviceFault NOTIFICATION-TYPE
        OBJECTS {
          efmCuPmeFltStatus
        }
        STATUS      current
        ::= { efmCuPmeNotifications 3 }

      efmCuPmeConfigInitFailure NOTIFICATION-TYPE
        OBJECTS {
          efmCuPmeFltStatus,
          efmCuAdminProfile,
          efmCuPmeAdminProfile
        }
        STATUS      current
        ::= { efmCuPmeNotifications 4 }

      efmCuPmeProtocolInitFailure NOTIFICATION-TYPE
        OBJECTS {
          efmCuPmeFltStatus,
          efmCuPmeOperSubType
        }
        STATUS     current
        ::= { efmCuPmeNotifications 5 }


      efmCuPmeConfTable OBJECT-TYPE
        SYNTAX      SEQUENCE OF EfmCuPmeConfEntry
        MAX-ACCESS  not-accessible
        STATUS      current
        ::= { efmCuPme 1 }

      efmCuPmeConfEntry OBJECT-TYPE
        SYNTAX      EfmCuPmeConfEntry
        MAX-ACCESS  not-accessible
        STATUS      current
        INDEX  { ifIndex }





        ::= { efmCuPmeConfTable 1 }

      EfmCuPmeConfEntry ::=
        SEQUENCE {
          efmCuPmeAdminSubType           INTEGER,
          efmCuPmeAdminProfile           EfmProfileIndexOrZero,
          efmCuPAFRemoteDiscoveryCode    PhysAddress,
          efmCuPmeThreshLineAtn          Integer32,
          efmCuPmeThreshSnrMgn           Integer32,
          efmCuPmeLineAtnCrossingEnable  TruthValue,
          efmCuPmeSnrMgnCrossingEnable   TruthValue,
          efmCuPmeDeviceFaultEnable      TruthValue,
          efmCuPmeConfigInitFailEnable   TruthValue,
          efmCuPmeProtocolInitFailEnable TruthValue
        }

      efmCuPmeAdminSubType  OBJECT-TYPE
        SYNTAX      INTEGER {
          ieee2BaseTLO(1),
          ieee2BaseTLR(2),
          ieee10PassTSO(3),
          ieee10PassTSR(4),
          ieee2BaseTLor10PassTSR(5),
          ieee2BaseTLor10PassTSO(6),
          ieee10PassTSor2BaseTLO(7)
        }
        MAX-ACCESS  read-write
        STATUS      current
        ::= { efmCuPmeConfEntry 1 }

      efmCuPmeAdminProfile  OBJECT-TYPE
        SYNTAX      EfmProfileIndexOrZero
        MAX-ACCESS  read-write
        STATUS      current
        DEFVAL { 0 }
        ::= { efmCuPmeConfEntry 2 }

      efmCuPAFRemoteDiscoveryCode  OBJECT-TYPE
        SYNTAX      PhysAddress (SIZE(0|6))
        MAX-ACCESS  read-write
        STATUS      current
        ::= { efmCuPmeConfEntry 3 }

      efmCuPmeThreshLineAtn  OBJECT-TYPE
        SYNTAX  Integer32(-127..128)
        UNITS       "dB"
        MAX-ACCESS  read-write
        STATUS      current
        ::= { efmCuPmeConfEntry 4 }

      efmCuPmeThreshSnrMgn  OBJECT-TYPE
        SYNTAX      Integer32(-127..128)
        UNITS       "dB"
        MAX-ACCESS  read-write
        STATUS      current
        ::= { efmCuPmeConfEntry 5 }

      efmCuPmeLineAtnCrossingEnable  OBJECT-TYPE
        SYNTAX      TruthValue
        MAX-ACCESS  read-write
        STATUS      current
        ::= { efmCuPmeConfEntry 6 }

      efmCuPmeSnrMgnCrossingEnable  OBJECT-TYPE
        SYNTAX      TruthValue
        MAX-ACCESS  read-write
        STATUS      current
        ::= { efmCuPmeConfEntry 7 }

      efmCuPmeDeviceFaultEnable  OBJECT-TYPE
        SYNTAX      TruthValue
        MAX-ACCESS  read-write
        STATUS      current
        ::= { efmCuPmeConfEntry 8 }

      efmCuPmeConfigInitFailEnable  OBJECT-TYPE
        SYNTAX      TruthValue
        MAX-ACCESS  read-write
        STATUS      current
        ::= { efmCuPmeConfEntry 9 }

      efmCuPmeProtocolInitFailEnable  OBJECT-TYPE
        SYNTAX      TruthValue
        MAX-ACCESS  read-write
        STATUS      current
        ::= { efmCuPmeConfEntry 10 }


      efmCuPmeCapabilityTable OBJECT-TYPE
        SYNTAX      SEQUENCE OF EfmCuPmeCapabilityEntry
        MAX-ACCESS  not-accessible
        STATUS      current
        ::= { efmCuPme 2 }





      efmCuPmeCapabilityEntry OBJECT-TYPE
        SYNTAX      EfmCuPmeCapabilityEntry
        MAX-ACCESS  not-accessible
        STATUS      current
        INDEX  { ifIndex }
        ::= { efmCuPmeCapabilityTable 1 }

      EfmCuPmeCapabilityEntry ::=
        SEQUENCE {
          efmCuPmeSubTypesSupported     BITS
        }

      efmCuPmeSubTypesSupported  OBJECT-TYPE
        SYNTAX      BITS {
          ieee2BaseTLO(0),
          ieee2BaseTLR(1),
          ieee10PassTSO(2),
          ieee10PassTSR(3)
        }
        MAX-ACCESS  read-only
        STATUS      current
        ::= { efmCuPmeCapabilityEntry 1 }





      efmCuPmeStatusTable OBJECT-TYPE
        SYNTAX      SEQUENCE OF EfmCuPmeStatusEntry
        MAX-ACCESS  not-accessible
        STATUS      current
        ::= { efmCuPme 3 }

      efmCuPmeStatusEntry OBJECT-TYPE
        SYNTAX      EfmCuPmeStatusEntry
        MAX-ACCESS  not-accessible
        STATUS      current
        INDEX  { ifIndex }
        ::= { efmCuPmeStatusTable 1 }

      EfmCuPmeStatusEntry ::=
        SEQUENCE {
          efmCuPmeOperStatus            INTEGER,
          efmCuPmeFltStatus             BITS,
          efmCuPmeOperSubType           INTEGER,
          efmCuPmeOperProfile           EfmProfileIndexOrZero,
          efmCuPmeSnrMgn                Integer32,
          efmCuPmePeerSnrMgn            Integer32,
          efmCuPmeLineAtn               Integer32,
          efmCuPmePeerLineAtn           Integer32,
          efmCuPmeEquivalentLength      Unsigned32,
          efmCuPmeTCCodingErrors        Counter32,
          efmCuPmeTCCrcErrors           Counter32
        }

      efmCuPmeOperStatus  OBJECT-TYPE
        SYNTAX      INTEGER {
          up(1),
          downNotReady(2),
          downReady(3),
          init(4)
        }





        MAX-ACCESS  read-only
        STATUS      current
        ::= { efmCuPmeStatusEntry 1 }

      efmCuPmeFltStatus  OBJECT-TYPE
        SYNTAX      BITS {
          lossOfFraming(0),
          snrMgnDefect(1),
          lineAtnDefect(2),
          deviceFault(3),
          configInitFailure(4),
          protocolInitFailure(5)
        }
        MAX-ACCESS  read-only
        STATUS      current
        ::= { efmCuPmeStatusEntry 2 }

      efmCuPmeOperSubType  OBJECT-TYPE
        SYNTAX      INTEGER {
          ieee2BaseTLO(1),
          ieee2BaseTLR(2),





          ieee10PassTSO(3),
          ieee10PassTSR(4)
        }
        MAX-ACCESS  read-only
        STATUS      current
        ::= { efmCuPmeStatusEntry 3 }

      efmCuPmeOperProfile  OBJECT-TYPE
        SYNTAX      EfmProfileIndexOrZero
        MAX-ACCESS  read-only
        STATUS      current
        ::= { efmCuPmeStatusEntry 4 }






      efmCuPmeSnrMgn OBJECT-TYPE
        SYNTAX      Integer32(-127..128|65535)
        UNITS       "dB"
        MAX-ACCESS  read-only
        STATUS      current
        ::= { efmCuPmeStatusEntry 5 }

      efmCuPmePeerSnrMgn OBJECT-TYPE
        SYNTAX      Integer32(-127..128|65535)
        UNITS       "dB"
        MAX-ACCESS  read-only
        STATUS      current
        ::= { efmCuPmeStatusEntry 6}

      efmCuPmeLineAtn OBJECT-TYPE
        SYNTAX      Integer32(-127..128|65535)
        UNITS       "dB"
        MAX-ACCESS  read-only
        STATUS      current
        ::= { efmCuPmeStatusEntry 7 }

      efmCuPmePeerLineAtn OBJECT-TYPE
        SYNTAX      Integer32(-127..128|65535)
        UNITS       "dB"
        MAX-ACCESS  read-only
        STATUS      current
        ::= { efmCuPmeStatusEntry 8 }

      efmCuPmeEquivalentLength  OBJECT-TYPE
        SYNTAX      Unsigned32(0..8192|65535)
        UNITS       "m"
        MAX-ACCESS  read-only
        STATUS      current





        ::= { efmCuPmeStatusEntry 9 }

      efmCuPmeTCCodingErrors OBJECT-TYPE
        SYNTAX      Counter32
        MAX-ACCESS  read-only
        STATUS      current
        ::= { efmCuPmeStatusEntry 10 }

      efmCuPmeTCCrcErrors OBJECT-TYPE
        SYNTAX      Counter32
        MAX-ACCESS  read-only
        STATUS      current





        ::= { efmCuPmeStatusEntry 11 }


      efmCuPme2B      OBJECT IDENTIFIER ::= { efmCuPme 5 }

      efmCuPme2BProfileTable OBJECT-TYPE
        SYNTAX      SEQUENCE OF EfmCuPme2BProfileEntry
        MAX-ACCESS  not-accessible
        STATUS      current
        ::= { efmCuPme2B  2 }





      efmCuPme2BProfileEntry OBJECT-TYPE
        SYNTAX      EfmCuPme2BProfileEntry
        MAX-ACCESS  not-accessible
        STATUS      current
        INDEX { efmCuPme2BProfileIndex }
        ::= { efmCuPme2BProfileTable 1 }

      EfmCuPme2BProfileEntry ::=
        SEQUENCE {
          efmCuPme2BProfileIndex           EfmProfileIndex,
          efmCuPme2BProfileDescr           SnmpAdminString,
          efmCuPme2BRegion                 INTEGER,
          efmCuPme2BsMode                  EfmProfileIndexOrZero,
          efmCuPme2BMinDataRate            Unsigned32,
          efmCuPme2BMaxDataRate            Unsigned32,
          efmCuPme2BPower                  Unsigned32,
          efmCuPme2BConstellation          INTEGER,
          efmCuPme2BProfileRowStatus       RowStatus
        }

      efmCuPme2BProfileIndex OBJECT-TYPE
        SYNTAX      EfmProfileIndex
        MAX-ACCESS  not-accessible
        STATUS      current
        ::= { efmCuPme2BProfileEntry 1 }






      efmCuPme2BProfileDescr OBJECT-TYPE
        SYNTAX      SnmpAdminString
        MAX-ACCESS  read-create
        STATUS      current
        ::= { efmCuPme2BProfileEntry 2 }

      efmCuPme2BRegion  OBJECT-TYPE
        SYNTAX      INTEGER {
          region1(1),
          region2(2)
        }
        MAX-ACCESS  read-create
        STATUS      current
        ::= { efmCuPme2BProfileEntry 3 }

      efmCuPme2BsMode  OBJECT-TYPE
        SYNTAX      EfmProfileIndexOrZero
        MAX-ACCESS  read-create
        STATUS      current
        DEFVAL { 0 }
        ::= { efmCuPme2BProfileEntry 4 }

      efmCuPme2BMinDataRate  OBJECT-TYPE
        SYNTAX  Unsigned32(192..5696)
        UNITS       "Kbps"
        MAX-ACCESS  read-create
        STATUS      current
        ::= { efmCuPme2BProfileEntry 5 }





      efmCuPme2BMaxDataRate  OBJECT-TYPE
        SYNTAX  Unsigned32(192..5696)
        UNITS       "Kbps"
        MAX-ACCESS  read-create
        STATUS      current
        ::= { efmCuPme2BProfileEntry 6 }

      efmCuPme2BPower  OBJECT-TYPE
        SYNTAX      Unsigned32(0|10..42)
        UNITS       "0.5 dBm"
        MAX-ACCESS  read-create
        STATUS      current





        ::= { efmCuPme2BProfileEntry 7 }

      efmCuPme2BConstellation  OBJECT-TYPE
        SYNTAX      INTEGER {
          adaptive(0),
          tcpam16(1),
          tcpam32(2)
        }
        MAX-ACCESS  read-create
        STATUS      current
        ::= { efmCuPme2BProfileEntry 8 }

      efmCuPme2BProfileRowStatus OBJECT-TYPE
        SYNTAX      RowStatus
        MAX-ACCESS  read-create
        STATUS      current
        ::= { efmCuPme2BProfileEntry 9 }






      efmCuPme2BsModeTable OBJECT-TYPE
        SYNTAX      SEQUENCE OF EfmCuPme2BsModeEntry
        MAX-ACCESS  not-accessible
        STATUS      current
        ::= { efmCuPme2B  3 }

      efmCuPme2BsModeEntry OBJECT-TYPE
        SYNTAX      EfmCuPme2BsModeEntry
        MAX-ACCESS  not-accessible
        STATUS      current
        INDEX { efmCuPme2BsModeIndex }
        ::= { efmCuPme2BsModeTable 1 }

      EfmCuPme2BsModeEntry ::=
        SEQUENCE {
          efmCuPme2BsModeIndex             EfmProfileIndex,
          efmCuPme2BsModeDescr             SnmpAdminString,
          efmCuPme2BsModeRowStatus         RowStatus
        }

      efmCuPme2BsModeIndex OBJECT-TYPE
        SYNTAX      EfmProfileIndex
        MAX-ACCESS  not-accessible
        STATUS      current





        ::= { efmCuPme2BsModeEntry 1 }

      efmCuPme2BsModeDescr OBJECT-TYPE
        SYNTAX      SnmpAdminString
        MAX-ACCESS  read-create
        STATUS      current
        ::= { efmCuPme2BsModeEntry 2 }

      efmCuPme2BsModeRowStatus OBJECT-TYPE
        SYNTAX      RowStatus
        MAX-ACCESS  read-create
        STATUS      current
        ::= { efmCuPme2BsModeEntry 3 }


      efmCuPme2BReachRateTable OBJECT-TYPE
        SYNTAX      SEQUENCE OF EfmCuPme2BReachRateEntry
        MAX-ACCESS  not-accessible
        STATUS      current
        ::= { efmCuPme2B  4 }

      efmCuPme2BReachRateEntry OBJECT-TYPE
        SYNTAX      EfmCuPme2BReachRateEntry
        MAX-ACCESS  not-accessible
        STATUS      current
        INDEX { efmCuPme2BsModeIndex, efmCuPme2BReachRateIndex }
        ::= { efmCuPme2BReachRateTable 1 }

      EfmCuPme2BReachRateEntry ::=
        SEQUENCE {
          efmCuPme2BReachRateIndex         EfmProfileIndex,
          efmCuPme2BEquivalentLength       Unsigned32,
          efmCuPme2BMaxDataRatePam16       Unsigned32,
          efmCuPme2BMaxDataRatePam32       Unsigned32,
          efmCuPme2BReachRateRowStatus     RowStatus
        }

      efmCuPme2BReachRateIndex OBJECT-TYPE
        SYNTAX      EfmProfileIndex
        MAX-ACCESS  not-accessible
        STATUS      current
        ::= { efmCuPme2BReachRateEntry 1 }

      efmCuPme2BEquivalentLength  OBJECT-TYPE
        SYNTAX      Unsigned32(0..8192)
        UNITS       "m"
        MAX-ACCESS  read-create
        STATUS      current
        ::= { efmCuPme2BReachRateEntry 2 }

      efmCuPme2BMaxDataRatePam16  OBJECT-TYPE
        SYNTAX      Unsigned32(0|192..5696)
        UNITS       "Kbps"
        MAX-ACCESS  read-create
        STATUS      current
        ::= { efmCuPme2BReachRateEntry 3 }

      efmCuPme2BMaxDataRatePam32  OBJECT-TYPE
        SYNTAX      Unsigned32(0|192..5696)
        UNITS       "Kbps"
        MAX-ACCESS  read-create
        STATUS      current
        ::= { efmCuPme2BReachRateEntry 4 }

      efmCuPme2BReachRateRowStatus OBJECT-TYPE
        SYNTAX      RowStatus
        MAX-ACCESS  read-create
        STATUS      current
        ::= { efmCuPme2BReachRateEntry 5 }








      efmCuPme10P      OBJECT IDENTIFIER ::= { efmCuPme 6 }

      efmCuPme10PProfileTable OBJECT-TYPE
        SYNTAX      SEQUENCE OF EfmCuPme10PProfileEntry
        MAX-ACCESS  not-accessible
        STATUS      current
        ::= { efmCuPme10P  1 }

      efmCuPme10PProfileEntry OBJECT-TYPE
        SYNTAX      EfmCuPme10PProfileEntry
        MAX-ACCESS  not-accessible
        STATUS      current
        INDEX { efmCuPme10PProfileIndex }
        ::= { efmCuPme10PProfileTable 1 }

      EfmCuPme10PProfileEntry ::=
        SEQUENCE {
          efmCuPme10PProfileIndex           EfmProfileIndex,
          efmCuPme10PProfileDescr           SnmpAdminString,
          efmCuPme10PBandplanPSDMskProfile  INTEGER,
          efmCuPme10PUPBOReferenceProfile   INTEGER,
          efmCuPme10PBandNotchProfiles      BITS,
          efmCuPme10PPayloadDRateProfile    INTEGER,
          efmCuPme10PPayloadURateProfile    INTEGER,
          efmCuPme10PProfileRowStatus       RowStatus
        }

      efmCuPme10PProfileIndex OBJECT-TYPE
        SYNTAX      EfmProfileIndex
        MAX-ACCESS  not-accessible
        STATUS      current





        ::= { efmCuPme10PProfileEntry 1 }

      efmCuPme10PProfileDescr OBJECT-TYPE
        SYNTAX      SnmpAdminString
        MAX-ACCESS  read-create
        STATUS      current
        ::= { efmCuPme10PProfileEntry 2 }

      efmCuPme10PBandplanPSDMskProfile  OBJECT-TYPE
        SYNTAX  INTEGER {
          profile1(1),
          profile2(2),
          profile3(3),
          profile4(4),
          profile5(5),
          profile6(6),
          profile7(7),
          profile8(8),
          profile9(9),
          profile10(10),
          profile11(11),
          profile12(12),
          profile13(13),
          profile14(14),
          profile15(15),
          profile16(16),
          profile17(17),
          profile18(18),
          profile19(19),
          profile20(20),
          profile21(21),
          profile22(22),
          profile23(23),
          profile24(24),
          profile25(25),
          profile26(26),
          profile27(27),
          profile28(28),
          profile29(29),
          profile30(30)
        }
        MAX-ACCESS  read-create
        STATUS      current
        ::= { efmCuPme10PProfileEntry 3 }

      efmCuPme10PUPBOReferenceProfile  OBJECT-TYPE
        SYNTAX  INTEGER {
          profile0(0),
          profile1(1),
          profile2(2),
          profile3(3),





          profile4(4),
          profile5(5),
          profile6(6),
          profile7(7),
          profile8(8),
          profile9(9)
        }
        MAX-ACCESS  read-create
        STATUS      current
        ::= { efmCuPme10PProfileEntry 4 }

      efmCuPme10PBandNotchProfiles  OBJECT-TYPE
        SYNTAX  BITS {
          profile0(0),
          profile1(1),
          profile2(2),
          profile3(3),
          profile4(4),
          profile5(5),
          profile6(6),
          profile7(7),
          profile8(8),
          profile9(9),
          profile10(10),
          profile11(11)
        }
        MAX-ACCESS  read-create





        STATUS      current
        ::= { efmCuPme10PProfileEntry 5 }

      efmCuPme10PPayloadDRateProfile  OBJECT-TYPE
        SYNTAX      INTEGER {
          profile5(5),
          profile10(10),
          profile15(15),
          profile20(20),
          profile25(25),
          profile30(30),
          profile50(50),
          profile70(70),
          profile100(100),
          profile140(140),
          profile200(200)
        }
        MAX-ACCESS  read-create
        STATUS      current
        ::= { efmCuPme10PProfileEntry 6 }

      efmCuPme10PPayloadURateProfile  OBJECT-TYPE
        SYNTAX      INTEGER {
          profile5(5),
          profile10(10),
          profile15(15),
          profile20(20),
          profile25(25),
          profile30(30),
          profile50(50),
          profile70(70),
          profile100(100)
        }
        MAX-ACCESS  read-create
        STATUS      current
        ::= { efmCuPme10PProfileEntry 7 }

      efmCuPme10PProfileRowStatus OBJECT-TYPE
        SYNTAX      RowStatus
        MAX-ACCESS  read-create
        STATUS      current
        ::= { efmCuPme10PProfileEntry 8 }


      efmCuPme10PStatusTable OBJECT-TYPE
        SYNTAX      SEQUENCE OF EfmCuPme10PStatusEntry
        MAX-ACCESS  not-accessible
        STATUS      current
        ::= { efmCuPme10P 2 }

      efmCuPme10PStatusEntry OBJECT-TYPE
        SYNTAX      EfmCuPme10PStatusEntry
        MAX-ACCESS  not-accessible
        STATUS      current
        INDEX  { ifIndex }





        ::= { efmCuPme10PStatusTable 1 }

      EfmCuPme10PStatusEntry ::=
        SEQUENCE {
          efmCuPme10PFECCorrectedBlocks     Counter32,
          efmCuPme10PFECUncorrectedBlocks   Counter32
        }

      efmCuPme10PFECCorrectedBlocks  OBJECT-TYPE
        SYNTAX      Counter32
        MAX-ACCESS  read-only
        STATUS      current
        ::= { efmCuPme10PStatusEntry 1 }

      efmCuPme10PFECUncorrectedBlocks  OBJECT-TYPE
        SYNTAX      Counter32
        MAX-ACCESS  read-only
        STATUS      current
        ::= { efmCuPme10PStatusEntry 2 }


      efmCuGroups      OBJECT IDENTIFIER ::= { efmCuConformance 1 }

      efmCuCompliances OBJECT IDENTIFIER ::= { efmCuConformance 2 }


      efmCuBasicGroup OBJECT-GROUP
        OBJECTS {
          efmCuPAFSupported,
          efmCuAdminProfile,
          efmCuTargetDataRate,
          efmCuTargetSnrMgn,
          efmCuAdaptiveSpectra,
          efmCuPortSide,
          efmCuFltStatus
        }
        STATUS      current
        ::= { efmCuGroups 1 }

      efmCuPAFGroup OBJECT-GROUP
        OBJECTS {
          efmCuPeerPAFSupported,
          efmCuPAFCapacity,
          efmCuPeerPAFCapacity,
          efmCuPAFAdminState,
          efmCuPAFDiscoveryCode,
          efmCuPAFRemoteDiscoveryCode,
          efmCuNumPMEs
        }
        STATUS      current
        ::= { efmCuGroups 2 }






      efmCuPAFErrorsGroup OBJECT-GROUP
        OBJECTS {
          efmCuPAFInErrors,
          efmCuPAFInSmallFragments,
          efmCuPAFInLargeFragments,
          efmCuPAFInBadFragments,
          efmCuPAFInLostFragments,
          efmCuPAFInLostStarts,
          efmCuPAFInLostEnds,
          efmCuPAFInOverflows
        }
        STATUS      current
        ::= { efmCuGroups 3 }

      efmCuPmeGroup OBJECT-GROUP
        OBJECTS {
          efmCuPmeAdminProfile,
          efmCuPmeOperStatus,
          efmCuPmeFltStatus,
          efmCuPmeSubTypesSupported,
          efmCuPmeAdminSubType,
          efmCuPmeOperSubType,
          efmCuPAFRemoteDiscoveryCode,
          efmCuPmeOperProfile,
          efmCuPmeSnrMgn,
          efmCuPmePeerSnrMgn,
          efmCuPmeLineAtn,
          efmCuPmePeerLineAtn,
          efmCuPmeEquivalentLength,
          efmCuPmeTCCodingErrors,
          efmCuPmeTCCrcErrors,
          efmCuPmeThreshLineAtn,
          efmCuPmeThreshSnrMgn
        }
        STATUS      current
        ::= { efmCuGroups 4 }

      efmCuAlarmConfGroup OBJECT-GROUP
        OBJECTS {
          efmCuThreshLowRate,
          efmCuLowRateCrossingEnable,
          efmCuPmeThreshLineAtn,





          efmCuPmeLineAtnCrossingEnable,
          efmCuPmeThreshSnrMgn,
          efmCuPmeSnrMgnCrossingEnable,
          efmCuPmeDeviceFaultEnable,
          efmCuPmeConfigInitFailEnable,
          efmCuPmeProtocolInitFailEnable
        }
        STATUS      current
        ::= { efmCuGroups 5 }

      efmCuNotificationGroup NOTIFICATION-GROUP
        NOTIFICATIONS {
          efmCuLowRateCrossing,
          efmCuPmeLineAtnCrossing,
          efmCuPmeSnrMgnCrossing,
          efmCuPmeDeviceFault,
          efmCuPmeConfigInitFailure,
          efmCuPmeProtocolInitFailure
        }
        STATUS      current
        ::= { efmCuGroups 6 }

      efmCuPme2BProfileGroup OBJECT-GROUP
        OBJECTS {
          efmCuPme2BProfileDescr,
          efmCuPme2BRegion,
          efmCuPme2BsMode,
          efmCuPme2BMinDataRate,
          efmCuPme2BMaxDataRate,
          efmCuPme2BPower,
          efmCuPme2BConstellation,
          efmCuPme2BProfileRowStatus,
          efmCuPme2BsModeDescr,
          efmCuPme2BsModeRowStatus,
          efmCuPme2BEquivalentLength,
          efmCuPme2BMaxDataRatePam16,
          efmCuPme2BMaxDataRatePam32,
          efmCuPme2BReachRateRowStatus
        }
        STATUS      current
        ::= { efmCuGroups 7}

      efmCuPme10PProfileGroup OBJECT-GROUP
        OBJECTS {
          efmCuPme10PProfileDescr,
          efmCuPme10PBandplanPSDMskProfile,
          efmCuPme10PUPBOReferenceProfile,
          efmCuPme10PBandNotchProfiles,
          efmCuPme10PPayloadDRateProfile,
          efmCuPme10PPayloadURateProfile,
          efmCuPme10PProfileRowStatus
        }
        STATUS  current
        ::= { efmCuGroups 8 }

      efmCuPme10PStatusGroup OBJECT-GROUP
        OBJECTS {
          efmCuPme10PFECCorrectedBlocks,
          efmCuPme10PFECUncorrectedBlocks
        }
        STATUS  current
        ::= { efmCuGroups 9 }


      efmCuCompliance MODULE-COMPLIANCE
        STATUS      current

        MODULE  -- this module
          MANDATORY-GROUPS {
            efmCuBasicGroup,
            efmCuPmeGroup,
            efmCuAlarmConfGroup,
            efmCuNotificationGroup
          }

          GROUP       efmCuPme2BProfileGroup

          GROUP       efmCuPme10PProfileGroup

          GROUP       efmCuPAFGroup

          GROUP       efmCuPAFErrorsGroup

          GROUP       efmCuPme10PStatusGroup

          OBJECT      efmCuPmeSubTypesSupported
          SYNTAX      BITS {
            ieee2BaseTLO(0),
            ieee2BaseTLR(1),
            ieee10PassTSO(2),
            ieee10PassTSR(3)
          }

          OBJECT      efmCuPmeAdminSubType
          MIN-ACCESS  read-only

          OBJECT      efmCuTargetSnrMgn
          MIN-ACCESS  read-only

          OBJECT      efmCuAdaptiveSpectra
          MIN-ACCESS  read-only

        ::= { efmCuCompliances 1 }
   END
