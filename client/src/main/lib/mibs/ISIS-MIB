ISIS-MIB DEFINITIONS ::= BEGIN
     IMPORTS
        TEXTUAL-CONVENTION, RowStatus, TruthValue, TimeStamp
                FROM SNMPv2-TC               -- RFC2579
        MODULE-IDENTITY, OBJECT-TYPE, NOTIFICATION-TYPE,
            Unsigned32, Counter32, mib-2
                FROM SNMPv2-SMI              -- RFC2578
        MODULE-COMPLIANCE, OBJECT-GROUP, NOTIFICATION-GROUP
                FROM SNMPv2-CONF             -- RFC2580
        SnmpAdminString
                FROM SNMP-FRAMEWORK-MIB      -- RFC2571
        IndexInteger, IndexIntegerNextFree
                FROM DIFFSERV-MIB            -- RFC3289
        InterfaceIndex
                FROM IF-MIB                  -- RFC2863
        InetAddressType, InetAddress, InetAddressPrefixLength
                FROM INET-ADDRESS-MIB;       -- RFC3291

    isisMIB MODULE-IDENTITY
        LAST-UPDATED "200604040000Z" -- April 4, 2006, midnight
        ORGANIZATION "IETF IS-IS for IP Internets Working Group"



    ::= { mib-2 138 }


isisNotifications       OBJECT IDENTIFIER ::= { isisMIB 0 }
isisObjects             OBJECT IDENTIFIER ::= { isisMIB 1 }
isisConformance         OBJECT IDENTIFIER ::= { isisMIB 2 }


isisSystem OBJECT IDENTIFIER ::= { isisObjects 1 }

isisSysLevel OBJECT IDENTIFIER ::= { isisObjects 2 }

isisCirc OBJECT IDENTIFIER ::= { isisObjects 3 }

isisCircLevelValues OBJECT IDENTIFIER ::= { isisObjects 4 }

isisCounters OBJECT IDENTIFIER ::= { isisObjects 5 }

isisISAdj OBJECT IDENTIFIER ::= { isisObjects 6 }

isisReachAddr OBJECT IDENTIFIER ::= { isisObjects 7 }

isisIPReachAddr OBJECT IDENTIFIER ::= { isisObjects 8 }

isisLSPDataBase OBJECT IDENTIFIER ::= { isisObjects 9 }

isisNotification OBJECT IDENTIFIER ::= { isisObjects 10 }






    IsisOSINSAddress ::= TEXTUAL-CONVENTION
        STATUS current
        SYNTAX OCTET STRING (SIZE(0..20))

    IsisSystemID ::= TEXTUAL-CONVENTION
        STATUS current
        SYNTAX OCTET STRING (SIZE(6))

    IsisLinkStatePDUID ::= TEXTUAL-CONVENTION
        STATUS current
        SYNTAX OCTET STRING (SIZE(8))

    IsisAdminState ::= TEXTUAL-CONVENTION
        STATUS current
        SYNTAX INTEGER
            {
                on(1),
                off(2)
            }

    IsisLSPBuffSize ::= TEXTUAL-CONVENTION
        DISPLAY-HINT "d"





        STATUS current
        SYNTAX Unsigned32 (512..16000)

    IsisLevelState ::= TEXTUAL-CONVENTION
        STATUS current
        SYNTAX INTEGER
            {
                off (1),
                on (2),
                waiting (3),
                overloaded(4)
            }

    IsisSupportedProtocol ::= TEXTUAL-CONVENTION
        STATUS current
        SYNTAX INTEGER
            {
                iso8473(129),
                ipV6(142),
                ip(204)
            }

    IsisDefaultMetric ::= TEXTUAL-CONVENTION
        DISPLAY-HINT "d"
        STATUS current
        SYNTAX Unsigned32 (0..63)

    IsisWideMetric ::= TEXTUAL-CONVENTION
        DISPLAY-HINT "d"
        STATUS current





        SYNTAX Unsigned32 (0..16777215)

    IsisFullMetric ::= TEXTUAL-CONVENTION
        DISPLAY-HINT "d"
        STATUS current
        SYNTAX Unsigned32

    IsisMetricType ::= TEXTUAL-CONVENTION
        STATUS current
        SYNTAX INTEGER
            {
                internal(1),
                external(2)
            }

    IsisMetricStyle ::= TEXTUAL-CONVENTION
        STATUS current
        SYNTAX INTEGER
            {
                narrow(1),
                wide(2),
                both(3)
            }

    IsisISLevel ::= TEXTUAL-CONVENTION
        STATUS current
        SYNTAX INTEGER
            {
                area(1),        -- L1
                domain(2)       -- L2
            }

    IsisLevel ::= TEXTUAL-CONVENTION
        STATUS current





        SYNTAX INTEGER
            {
                level1(1),
                level2(2),
                level1and2(3)
            }

    IsisPDUHeader ::= TEXTUAL-CONVENTION
        STATUS current
        SYNTAX OCTET STRING (SIZE(0..64))

    IsisCircuitID ::= TEXTUAL-CONVENTION
        STATUS current
        SYNTAX OCTET STRING (SIZE(0|7))

    IsisISPriority ::= TEXTUAL-CONVENTION
        DISPLAY-HINT "d"
        STATUS current
        SYNTAX Unsigned32 (0..127)

    IsisUnsigned16TC ::= TEXTUAL-CONVENTION
        DISPLAY-HINT "d"
        STATUS current
        SYNTAX Unsigned32 (0..65535)

    IsisUnsigned8TC ::= TEXTUAL-CONVENTION
        DISPLAY-HINT "d"
        STATUS current
        SYNTAX Unsigned32 (0..255)










    isisSysObject  OBJECT IDENTIFIER ::= { isisSystem 1 }

    isisSysVersion OBJECT-TYPE
        SYNTAX INTEGER
            {
                unknown(0),
                one(1)
            }
        MAX-ACCESS read-only
        STATUS current
        DEFVAL { one }
    ::= { isisSysObject 1 }

    isisSysLevelType OBJECT-TYPE
        SYNTAX IsisLevel





        MAX-ACCESS read-write
        STATUS current
        DEFVAL { level1and2 }
    ::= { isisSysObject 2 }

    isisSysID OBJECT-TYPE
        SYNTAX IsisSystemID
        MAX-ACCESS read-write
        STATUS current
    ::= { isisSysObject 3 }

    isisSysMaxPathSplits OBJECT-TYPE
        SYNTAX Unsigned32 (1..32)
        MAX-ACCESS read-write
        STATUS current
        DEFVAL { 2 }
    ::= { isisSysObject 4 }

    isisSysMaxLSPGenInt OBJECT-TYPE
        SYNTAX Unsigned32 (1..65235)





        UNITS "seconds"
        MAX-ACCESS read-write
        STATUS current
        DEFVAL { 900 }
    ::= { isisSysObject 5 }

    isisSysPollESHelloRate OBJECT-TYPE
        SYNTAX IsisUnsigned16TC (1..65535)
        UNITS "seconds"
        MAX-ACCESS read-write
        STATUS current
        DEFVAL { 50 }
    ::= { isisSysObject 6 }

    isisSysWaitTime OBJECT-TYPE
        SYNTAX IsisUnsigned16TC (1..65535)
        UNITS "seconds"
        MAX-ACCESS read-write
        STATUS current
        DEFVAL { 60 }
    ::= { isisSysObject 7 }

    isisSysAdminState OBJECT-TYPE
        SYNTAX IsisAdminState





        MAX-ACCESS read-write
        STATUS current
        DEFVAL { off }
    ::= { isisSysObject 8 }

    isisSysL2toL1Leaking OBJECT-TYPE
        SYNTAX TruthValue
        MAX-ACCESS read-write
        STATUS current
        DEFVAL { false }
    ::= { isisSysObject 9 }

    isisSysMaxAge OBJECT-TYPE
        SYNTAX IsisUnsigned16TC (350..65535)
        UNITS "seconds"
        MAX-ACCESS read-write
        STATUS current
        DEFVAL { 1200 }
    ::= { isisSysObject 10 }

    isisSysReceiveLSPBufferSize OBJECT-TYPE
        SYNTAX IsisUnsigned16TC (1492..16000)
        UNITS "bytes"
        MAX-ACCESS read-write
        STATUS current
        DEFVAL { 1492 }
    ::= { isisSysObject 11 }

    isisSysProtSupported OBJECT-TYPE
        SYNTAX BITS {
                    iso8473 (0),
                    ipv4 (1),
                    ipv6 (2)
                  }
        MAX-ACCESS read-only
        STATUS current
    ::= { isisSysObject 12 }

    isisSysNotificationEnable OBJECT-TYPE
        SYNTAX TruthValue
        MAX-ACCESS read-write
        STATUS current
        DEFVAL { true }
    ::= { isisSysObject 13 }


    isisManAreaAddrTable OBJECT-TYPE
        SYNTAX SEQUENCE OF IsisManAreaAddrEntry
        MAX-ACCESS not-accessible
        STATUS current
    ::= { isisSystem 2 }

    isisManAreaAddrEntry OBJECT-TYPE
        SYNTAX IsisManAreaAddrEntry
        MAX-ACCESS not-accessible
        STATUS current
        INDEX { isisManAreaAddr }
    ::= { isisManAreaAddrTable 1 }

    IsisManAreaAddrEntry ::=
        SEQUENCE {
            isisManAreaAddr
                IsisOSINSAddress,
            isisManAreaAddrExistState
                RowStatus
            }

    isisManAreaAddr OBJECT-TYPE
        SYNTAX IsisOSINSAddress
        MAX-ACCESS not-accessible
        STATUS current
    ::= { isisManAreaAddrEntry 1 }

    isisManAreaAddrExistState OBJECT-TYPE
        SYNTAX RowStatus
        MAX-ACCESS read-create
        STATUS current
    ::= { isisManAreaAddrEntry 2 }



    isisAreaAddrTable OBJECT-TYPE
        SYNTAX SEQUENCE OF IsisAreaAddrEntry
        MAX-ACCESS not-accessible
        STATUS current
    ::= { isisSystem 3 }

    isisAreaAddrEntry OBJECT-TYPE
        SYNTAX IsisAreaAddrEntry
        MAX-ACCESS not-accessible
        STATUS current
        INDEX { isisAreaAddr }
    ::= { isisAreaAddrTable 1 }

    IsisAreaAddrEntry ::=
        SEQUENCE {
            isisAreaAddr
                IsisOSINSAddress
            }






    isisAreaAddr OBJECT-TYPE
        SYNTAX IsisOSINSAddress
        MAX-ACCESS read-only
        STATUS current
    ::= { isisAreaAddrEntry 1 }



    isisSummAddrTable OBJECT-TYPE
        SYNTAX SEQUENCE OF IsisSummAddrEntry
        MAX-ACCESS not-accessible
        STATUS current
    ::= { isisSystem 4 }

    isisSummAddrEntry OBJECT-TYPE
        SYNTAX IsisSummAddrEntry
        MAX-ACCESS not-accessible
        STATUS current
        INDEX { isisSummAddressType,
                isisSummAddress,
                isisSummAddrPrefixLen }





    ::= { isisSummAddrTable 1 }

    IsisSummAddrEntry ::=
        SEQUENCE {
            isisSummAddressType
                InetAddressType,
            isisSummAddress
                InetAddress,
            isisSummAddrPrefixLen
                InetAddressPrefixLength,
            isisSummAddrExistState
                RowStatus,
            isisSummAddrMetric
                IsisDefaultMetric,
            isisSummAddrFullMetric
                IsisFullMetric
        }

    isisSummAddressType OBJECT-TYPE
        SYNTAX InetAddressType
        MAX-ACCESS not-accessible
        STATUS current
    ::= { isisSummAddrEntry 1 }

    isisSummAddress OBJECT-TYPE
        SYNTAX InetAddress
        MAX-ACCESS not-accessible
        STATUS current
    ::= { isisSummAddrEntry 2 }

    isisSummAddrPrefixLen OBJECT-TYPE
        SYNTAX InetAddressPrefixLength
        MAX-ACCESS not-accessible
        STATUS current
    ::= { isisSummAddrEntry 3 }

    isisSummAddrExistState OBJECT-TYPE
        SYNTAX RowStatus
        MAX-ACCESS read-create
        STATUS current
    ::= { isisSummAddrEntry 4 }

    isisSummAddrMetric OBJECT-TYPE
        SYNTAX IsisDefaultMetric
        MAX-ACCESS read-create
        STATUS current
        DEFVAL { 20 }
    ::= { isisSummAddrEntry 5 }

    isisSummAddrFullMetric OBJECT-TYPE
        SYNTAX IsisFullMetric
        MAX-ACCESS read-create
        STATUS current
        DEFVAL { 20 }
    ::= { isisSummAddrEntry 6 }


    isisRedistributeAddrTable OBJECT-TYPE
        SYNTAX SEQUENCE OF IsisRedistributeAddrEntry
        MAX-ACCESS not-accessible





        STATUS current
    ::= { isisSystem 5 }

    isisRedistributeAddrEntry OBJECT-TYPE
        SYNTAX IsisRedistributeAddrEntry
        MAX-ACCESS not-accessible
        STATUS current
        INDEX { isisRedistributeAddrType,
                isisRedistributeAddrAddress,
                isisRedistributeAddrPrefixLen }
    ::= { isisRedistributeAddrTable 1 }

    IsisRedistributeAddrEntry ::=
        SEQUENCE {
            isisRedistributeAddrType
                InetAddressType,
            isisRedistributeAddrAddress
                InetAddress,
            isisRedistributeAddrPrefixLen
                InetAddressPrefixLength,
            isisRedistributeAddrExistState
                RowStatus
        }

    isisRedistributeAddrType OBJECT-TYPE





        SYNTAX InetAddressType
        MAX-ACCESS not-accessible
        STATUS current
    ::= { isisRedistributeAddrEntry 1 }

    isisRedistributeAddrAddress OBJECT-TYPE
        SYNTAX InetAddress
        MAX-ACCESS not-accessible
        STATUS current

    ::= { isisRedistributeAddrEntry 2 }

    isisRedistributeAddrPrefixLen OBJECT-TYPE
        SYNTAX InetAddressPrefixLength
        MAX-ACCESS not-accessible
        STATUS current

    ::= { isisRedistributeAddrEntry 3 }

    isisRedistributeAddrExistState OBJECT-TYPE
        SYNTAX RowStatus
        MAX-ACCESS read-create
        STATUS current
    ::= { isisRedistributeAddrEntry 4 }


    isisRouterTable OBJECT-TYPE
        SYNTAX SEQUENCE OF IsisRouterEntry
        MAX-ACCESS not-accessible
        STATUS current
    ::= { isisSystem 6 }

    isisRouterEntry OBJECT-TYPE
        SYNTAX IsisRouterEntry
        MAX-ACCESS not-accessible
        STATUS current
        INDEX { isisRouterSysID,
                isisRouterLevel }
    ::= { isisRouterTable 1 }

    IsisRouterEntry ::=
        SEQUENCE {
            isisRouterSysID
                IsisSystemID,
            isisRouterLevel
                IsisISLevel,
            isisRouterHostName
                SnmpAdminString,
            isisRouterID
                Unsigned32
        }

    isisRouterSysID OBJECT-TYPE
        SYNTAX IsisSystemID
        MAX-ACCESS not-accessible
        STATUS current





    ::= { isisRouterEntry 1 }

    isisRouterLevel OBJECT-TYPE
        SYNTAX IsisISLevel
        MAX-ACCESS not-accessible
        STATUS current
    ::= { isisRouterEntry 2 }

    isisRouterHostName OBJECT-TYPE
        SYNTAX SnmpAdminString
        MAX-ACCESS read-only
        STATUS current
    ::= { isisRouterEntry 3 }

    isisRouterID OBJECT-TYPE
        SYNTAX Unsigned32
        MAX-ACCESS read-only
        STATUS current
    ::= { isisRouterEntry 4 }


    isisSysLevelTable OBJECT-TYPE
        SYNTAX SEQUENCE OF IsisSysLevelEntry
        MAX-ACCESS not-accessible
        STATUS current
    ::= { isisSysLevel 1 }

    isisSysLevelEntry OBJECT-TYPE
        SYNTAX IsisSysLevelEntry
        MAX-ACCESS not-accessible
        STATUS current
        INDEX { isisSysLevelIndex }





    ::= { isisSysLevelTable 1 }

    IsisSysLevelEntry ::=
        SEQUENCE {
            isisSysLevelIndex
                IsisISLevel,
            isisSysLevelOrigLSPBuffSize
                IsisLSPBuffSize,
            isisSysLevelMinLSPGenInt
                IsisUnsigned16TC,
            isisSysLevelState
                IsisLevelState,
            isisSysLevelSetOverload
                TruthValue,
            isisSysLevelSetOverloadUntil
                Unsigned32,
            isisSysLevelMetricStyle
                IsisMetricStyle,
            isisSysLevelSPFConsiders
                IsisMetricStyle,
            isisSysLevelTEEnabled
                TruthValue
        }

    isisSysLevelIndex OBJECT-TYPE
        SYNTAX IsisISLevel
        MAX-ACCESS not-accessible
        STATUS current
    ::= { isisSysLevelEntry 1 }

    isisSysLevelOrigLSPBuffSize OBJECT-TYPE
        SYNTAX IsisLSPBuffSize
        MAX-ACCESS read-write
        STATUS current
        DEFVAL { 1492 }
    ::= { isisSysLevelEntry 2 }

    isisSysLevelMinLSPGenInt OBJECT-TYPE
        SYNTAX IsisUnsigned16TC (1..65535)
        UNITS "seconds"





        MAX-ACCESS read-write
        STATUS current
        DEFVAL { 30 }
    ::= { isisSysLevelEntry 3 }

    isisSysLevelState OBJECT-TYPE
        SYNTAX IsisLevelState
        MAX-ACCESS read-only
        STATUS current
    ::= { isisSysLevelEntry 4 }

    isisSysLevelSetOverload OBJECT-TYPE
        SYNTAX TruthValue
        MAX-ACCESS read-write
        STATUS current
        DEFVAL { false }
    ::= { isisSysLevelEntry 5 }

    isisSysLevelSetOverloadUntil OBJECT-TYPE
        SYNTAX Unsigned32
        UNITS "Seconds until clearing manually set Overload Bit"
        MAX-ACCESS read-write
        STATUS current





    ::= { isisSysLevelEntry 6 }

    isisSysLevelMetricStyle OBJECT-TYPE
        SYNTAX IsisMetricStyle
        MAX-ACCESS read-write
        STATUS current
        DEFVAL { narrow }
    ::= { isisSysLevelEntry 7 }

    isisSysLevelSPFConsiders OBJECT-TYPE
        SYNTAX IsisMetricStyle
        MAX-ACCESS read-write
        STATUS current
        DEFVAL { narrow }
    ::= { isisSysLevelEntry 8 }

    isisSysLevelTEEnabled OBJECT-TYPE
        SYNTAX TruthValue
        MAX-ACCESS read-write
        STATUS current
        DEFVAL { false }
    ::= { isisSysLevelEntry 9 }


    isisNextCircIndex OBJECT-TYPE
        SYNTAX IndexIntegerNextFree





        MAX-ACCESS read-only
        STATUS current
    ::= { isisCirc  1 }


    isisCircTable OBJECT-TYPE
        SYNTAX SEQUENCE OF IsisCircEntry
        MAX-ACCESS not-accessible
        STATUS current
    ::= { isisCirc 2 }

    isisCircEntry OBJECT-TYPE
        SYNTAX IsisCircEntry
        MAX-ACCESS not-accessible
        STATUS current
        INDEX { isisCircIndex }
    ::= { isisCircTable 1 }






    IsisCircEntry ::=
        SEQUENCE {
            isisCircIndex
                IndexInteger,
            isisCircIfIndex
                InterfaceIndex,
            isisCircAdminState
                IsisAdminState,
            isisCircExistState
                RowStatus,
            isisCircType
                INTEGER,
            isisCircExtDomain
                TruthValue,
            isisCircLevelType
                IsisLevel,
            isisCircPassiveCircuit
                TruthValue,
            isisCircMeshGroupEnabled
                INTEGER,
            isisCircMeshGroup
                Unsigned32,
            isisCircSmallHellos
                TruthValue,
            isisCircLastUpTime
                TimeStamp,
            isisCirc3WayEnabled
                TruthValue,
            isisCircExtendedCircID
                Unsigned32
        }

    isisCircIndex OBJECT-TYPE
        SYNTAX IndexInteger
        MAX-ACCESS not-accessible
        STATUS current
    ::= { isisCircEntry 1 }

    isisCircIfIndex OBJECT-TYPE
        SYNTAX InterfaceIndex





        MAX-ACCESS read-create
        STATUS current
    ::= { isisCircEntry 2 }

    isisCircAdminState OBJECT-TYPE
        SYNTAX IsisAdminState
        MAX-ACCESS read-create
        STATUS current
        DEFVAL { off }
    ::= { isisCircEntry 3 }

    isisCircExistState OBJECT-TYPE
        SYNTAX RowStatus
        MAX-ACCESS read-create
        STATUS current
    ::= { isisCircEntry 4 }

    isisCircType OBJECT-TYPE
        SYNTAX INTEGER
            {
                broadcast(1),
                ptToPt(2),
                staticIn(3),
                staticOut(4),
                dA(5)
            }
        MAX-ACCESS read-create
        STATUS current
    ::= { isisCircEntry 5 }

    isisCircExtDomain OBJECT-TYPE
        SYNTAX TruthValue
        MAX-ACCESS read-create
        STATUS current
        DEFVAL { false }
    ::= { isisCircEntry 6 }

    isisCircLevelType OBJECT-TYPE
        SYNTAX IsisLevel
        MAX-ACCESS read-create
        STATUS current
        DEFVAL { level1and2 }
    ::= { isisCircEntry 7 }

    isisCircPassiveCircuit OBJECT-TYPE
        SYNTAX TruthValue
        MAX-ACCESS read-create
        STATUS current
        DEFVAL { false }
    ::= { isisCircEntry 8 }

    isisCircMeshGroupEnabled OBJECT-TYPE
        SYNTAX INTEGER
            {
                inactive(1),
                blocked(2),
                set(3)





            }
        MAX-ACCESS read-create
        STATUS current
        DEFVAL { inactive }
    ::= { isisCircEntry 9 }

    isisCircMeshGroup OBJECT-TYPE
        SYNTAX Unsigned32
        MAX-ACCESS read-create
        STATUS current
    ::= { isisCircEntry 10 }

    isisCircSmallHellos OBJECT-TYPE
        SYNTAX TruthValue
        MAX-ACCESS read-create
        STATUS current
         DEFVAL { false }
    ::= { isisCircEntry 11 }

    isisCircLastUpTime OBJECT-TYPE
        SYNTAX TimeStamp
        MAX-ACCESS read-only
        STATUS current





    ::= { isisCircEntry 12 }

    isisCirc3WayEnabled OBJECT-TYPE
        SYNTAX TruthValue
        MAX-ACCESS read-create
        STATUS current
        DEFVAL { true }
    ::= { isisCircEntry 13 }

    isisCircExtendedCircID OBJECT-TYPE
        SYNTAX Unsigned32
        MAX-ACCESS read-create
        STATUS current
    ::= { isisCircEntry 14 }


    isisCircLevelTable OBJECT-TYPE
        SYNTAX SEQUENCE OF IsisCircLevelEntry
        MAX-ACCESS not-accessible
        STATUS current
    ::= { isisCircLevelValues 1 }

    isisCircLevelEntry OBJECT-TYPE
        SYNTAX IsisCircLevelEntry
        MAX-ACCESS not-accessible
        STATUS current
        INDEX { isisCircIndex,
                isisCircLevelIndex }
    ::= { isisCircLevelTable 1 }

    IsisCircLevelEntry ::=





        SEQUENCE {
            isisCircLevelIndex
                IsisISLevel,
            isisCircLevelMetric
                IsisDefaultMetric,
            isisCircLevelWideMetric
                IsisWideMetric,
            isisCircLevelISPriority
                IsisISPriority,
            isisCircLevelIDOctet
                Unsigned32,
            isisCircLevelID
                IsisCircuitID,
            isisCircLevelDesIS
                IsisCircuitID,
            isisCircLevelHelloMultiplier
                Unsigned32,
            isisCircLevelHelloTimer
                Unsigned32,
            isisCircLevelDRHelloTimer
                Unsigned32,
            isisCircLevelLSPThrottle
                IsisUnsigned16TC,
            isisCircLevelMinLSPRetransInt
                Unsigned32,
            isisCircLevelCSNPInterval
                Unsigned32,
            isisCircLevelPartSNPInterval
                Unsigned32
        }

    isisCircLevelIndex OBJECT-TYPE
        SYNTAX IsisISLevel
        MAX-ACCESS not-accessible
        STATUS current
    ::= { isisCircLevelEntry 1 }

    isisCircLevelMetric OBJECT-TYPE
        SYNTAX IsisDefaultMetric
        MAX-ACCESS read-write
        STATUS current
        DEFVAL { 10 }
    ::= { isisCircLevelEntry 2 }





    isisCircLevelWideMetric OBJECT-TYPE
        SYNTAX IsisWideMetric
        MAX-ACCESS read-write
        STATUS current
        DEFVAL { 10 }
    ::= { isisCircLevelEntry 3 }

    isisCircLevelISPriority OBJECT-TYPE
        SYNTAX IsisISPriority
        MAX-ACCESS read-write
        STATUS current
        DEFVAL { 64 }
    ::= { isisCircLevelEntry 4 }

    isisCircLevelIDOctet OBJECT-TYPE
        SYNTAX Unsigned32(0..255)
        MAX-ACCESS read-only
        STATUS current
    ::= { isisCircLevelEntry 5 }

    isisCircLevelID OBJECT-TYPE
        SYNTAX IsisCircuitID
        MAX-ACCESS read-only
        STATUS current
    ::= { isisCircLevelEntry 6 }

    isisCircLevelDesIS OBJECT-TYPE
        SYNTAX IsisCircuitID
        MAX-ACCESS read-only
        STATUS current
    ::= { isisCircLevelEntry 7 }

    isisCircLevelHelloMultiplier OBJECT-TYPE
        SYNTAX Unsigned32 (2..100)
        MAX-ACCESS read-write
        STATUS current
        DEFVAL { 10 }
    ::= { isisCircLevelEntry 8 }

    isisCircLevelHelloTimer OBJECT-TYPE
        SYNTAX Unsigned32 (10..600000)
        UNITS "milliseconds"
        MAX-ACCESS read-write
        STATUS current
        DEFVAL { 3000 }
    ::= { isisCircLevelEntry 9 }

    isisCircLevelDRHelloTimer OBJECT-TYPE
        SYNTAX Unsigned32 (10..120000)
        UNITS "milliseconds"
        MAX-ACCESS read-write
        STATUS current
        DEFVAL { 1000 }
    ::= { isisCircLevelEntry 10 }

    isisCircLevelLSPThrottle OBJECT-TYPE
        SYNTAX IsisUnsigned16TC (1..65535)
        UNITS "milliseconds"
        MAX-ACCESS read-write
        STATUS current
        DEFVAL { 30 }
    ::= { isisCircLevelEntry 11 }

    isisCircLevelMinLSPRetransInt OBJECT-TYPE
        SYNTAX Unsigned32 (1..300)
        UNITS "seconds"
        MAX-ACCESS read-write
        STATUS current
        DEFVAL { 5 }
    ::= { isisCircLevelEntry 12 }





    isisCircLevelCSNPInterval OBJECT-TYPE
        SYNTAX Unsigned32 (1..600)
        UNITS "seconds"
        MAX-ACCESS read-write
        STATUS current
        DEFVAL { 10 }
    ::= { isisCircLevelEntry 13 }

    isisCircLevelPartSNPInterval OBJECT-TYPE
        SYNTAX Unsigned32 (1..120)
        UNITS "seconds"
        MAX-ACCESS read-write
        STATUS current
        DEFVAL { 2 }
    ::= { isisCircLevelEntry 14 }


    isisSystemCounterTable OBJECT-TYPE
        SYNTAX SEQUENCE OF IsisSystemCounterEntry
        MAX-ACCESS not-accessible
        STATUS current
    ::= { isisCounters 1 }

    isisSystemCounterEntry OBJECT-TYPE
        SYNTAX IsisSystemCounterEntry
        MAX-ACCESS not-accessible
        STATUS current
        INDEX { isisSysStatLevel }
    ::= { isisSystemCounterTable 1 }

    IsisSystemCounterEntry ::=





        SEQUENCE {
            isisSysStatLevel
                IsisISLevel,
            isisSysStatCorrLSPs
                Counter32,
            isisSysStatAuthTypeFails
                Counter32,
            isisSysStatAuthFails
                Counter32,
            isisSysStatLSPDbaseOloads
                Counter32,
            isisSysStatManAddrDropFromAreas
                Counter32,
            isisSysStatAttmptToExMaxSeqNums
                Counter32,
            isisSysStatSeqNumSkips
                Counter32,
            isisSysStatOwnLSPPurges
                Counter32,
            isisSysStatIDFieldLenMismatches
                Counter32,
            isisSysStatPartChanges
                Counter32,
            isisSysStatSPFRuns
                Counter32,
            isisSysStatLSPErrors
                Counter32
        }

    isisSysStatLevel OBJECT-TYPE
        SYNTAX IsisISLevel
        MAX-ACCESS not-accessible
        STATUS current
    ::= { isisSystemCounterEntry 1 }

    isisSysStatCorrLSPs OBJECT-TYPE
        SYNTAX Counter32
        UNITS "Number of corrupted in-memory frames"
        MAX-ACCESS read-only
        STATUS current
    ::= { isisSystemCounterEntry 2 }

    isisSysStatAuthTypeFails OBJECT-TYPE
        SYNTAX Counter32
        UNITS "Number of frames with authentication type mismatches"
        MAX-ACCESS read-only
        STATUS current
    ::= { isisSystemCounterEntry 3 }

    isisSysStatAuthFails OBJECT-TYPE
        SYNTAX Counter32
        UNITS "Number of frames with authentication key failures"
        MAX-ACCESS read-only
        STATUS current
    ::= { isisSystemCounterEntry 4 }

    isisSysStatLSPDbaseOloads OBJECT-TYPE
        SYNTAX Counter32
        MAX-ACCESS read-only
        STATUS current
    ::= { isisSystemCounterEntry 5 }

    isisSysStatManAddrDropFromAreas OBJECT-TYPE
        SYNTAX Counter32
        MAX-ACCESS read-only
        STATUS current
    ::= { isisSystemCounterEntry 6 }

    isisSysStatAttmptToExMaxSeqNums OBJECT-TYPE
        SYNTAX Counter32
        MAX-ACCESS read-only





        STATUS current
    ::= { isisSystemCounterEntry 7 }

    isisSysStatSeqNumSkips OBJECT-TYPE
        SYNTAX Counter32
        MAX-ACCESS read-only
        STATUS current
    ::= { isisSystemCounterEntry 8 }

    isisSysStatOwnLSPPurges OBJECT-TYPE
        SYNTAX Counter32
        MAX-ACCESS read-only
        STATUS current
    ::= { isisSystemCounterEntry 9 }

    isisSysStatIDFieldLenMismatches OBJECT-TYPE
        SYNTAX Counter32
        UNITS "Number of frames with ID length mismatches"
        MAX-ACCESS read-only
        STATUS current
    ::= { isisSystemCounterEntry 10 }

    isisSysStatPartChanges OBJECT-TYPE
        SYNTAX Counter32
        MAX-ACCESS read-only
        STATUS current
    ::= { isisSystemCounterEntry 11 }

    isisSysStatSPFRuns OBJECT-TYPE
        SYNTAX Counter32





        MAX-ACCESS read-only
        STATUS current
    ::= { isisSystemCounterEntry 12 }

    isisSysStatLSPErrors OBJECT-TYPE
        SYNTAX Counter32
        UNITS "Number of frames with errors that we have received"
        MAX-ACCESS read-only
        STATUS current
    ::= { isisSystemCounterEntry 13 }


    isisCircuitCounterTable OBJECT-TYPE
        SYNTAX SEQUENCE OF IsisCircuitCounterEntry
        MAX-ACCESS not-accessible
        STATUS current
    ::= { isisCounters 2 }

    isisCircuitCounterEntry OBJECT-TYPE
        SYNTAX IsisCircuitCounterEntry
        MAX-ACCESS not-accessible
        STATUS current
        INDEX { isisCircIndex,
                isisCircuitType }
    ::= { isisCircuitCounterTable 1 }

    IsisCircuitCounterEntry ::= SEQUENCE {
          isisCircuitType
              INTEGER,
          isisCircAdjChanges
              Counter32,
          isisCircNumAdj
              Unsigned32,
          isisCircInitFails
              Counter32,
          isisCircRejAdjs





              Counter32,
          isisCircIDFieldLenMismatches
              Counter32,
          isisCircMaxAreaAddrMismatches
              Counter32,
          isisCircAuthTypeFails
              Counter32,
          isisCircAuthFails
              Counter32,
          isisCircLANDesISChanges
              Counter32
       }

    isisCircuitType OBJECT-TYPE
        SYNTAX INTEGER
            {
                lanlevel1(1),
                lanlevel2(2),
                p2pcircuit(3)
            }
        MAX-ACCESS not-accessible
        STATUS current
    ::= { isisCircuitCounterEntry 1 }

    isisCircAdjChanges OBJECT-TYPE
        SYNTAX Counter32
        MAX-ACCESS read-only
        STATUS current
    ::= { isisCircuitCounterEntry 2 }

    isisCircNumAdj OBJECT-TYPE
        SYNTAX Unsigned32
        MAX-ACCESS read-only
        STATUS current





    ::= { isisCircuitCounterEntry 3 }

    isisCircInitFails OBJECT-TYPE
        SYNTAX Counter32
        MAX-ACCESS read-only
        STATUS current
    ::= { isisCircuitCounterEntry 4 }

    isisCircRejAdjs OBJECT-TYPE
        SYNTAX Counter32
        MAX-ACCESS read-only
        STATUS current
    ::= { isisCircuitCounterEntry 5 }

    isisCircIDFieldLenMismatches OBJECT-TYPE
        SYNTAX Counter32
        UNITS "Number of frames with ID field length mismatch"
        MAX-ACCESS read-only
        STATUS current
    ::= { isisCircuitCounterEntry 6 }

    isisCircMaxAreaAddrMismatches OBJECT-TYPE
        SYNTAX Counter32
        MAX-ACCESS read-only
        STATUS current
    ::= { isisCircuitCounterEntry 7 }

    isisCircAuthTypeFails OBJECT-TYPE





        SYNTAX Counter32
        MAX-ACCESS read-only
        STATUS current
    ::= { isisCircuitCounterEntry 8 }

    isisCircAuthFails OBJECT-TYPE
        SYNTAX Counter32
        MAX-ACCESS read-only
        STATUS current
    ::= { isisCircuitCounterEntry 9 }

    isisCircLANDesISChanges OBJECT-TYPE
        SYNTAX Counter32
        MAX-ACCESS read-only
        STATUS current
    ::= { isisCircuitCounterEntry 10 }


    isisPacketCounterTable OBJECT-TYPE
        SYNTAX SEQUENCE OF IsisPacketCounterEntry
        MAX-ACCESS not-accessible
        STATUS current
    ::= { isisCounters 3 }

    isisPacketCounterEntry OBJECT-TYPE
        SYNTAX IsisPacketCounterEntry
        MAX-ACCESS not-accessible
        STATUS current





        INDEX { isisCircIndex,
                isisPacketCountLevel,
                isisPacketCountDirection }
    ::= { isisPacketCounterTable 1 }

    IsisPacketCounterEntry ::=
        SEQUENCE {
            isisPacketCountLevel
                IsisISLevel,
            isisPacketCountDirection
                INTEGER,
            isisPacketCountIIHello
                Counter32,
            isisPacketCountISHello
                Counter32,
            isisPacketCountESHello
                Counter32,
            isisPacketCountLSP
                Counter32,
            isisPacketCountCSNP
                Counter32,
            isisPacketCountPSNP
                Counter32,
            isisPacketCountUnknown
                Counter32
    }

    isisPacketCountLevel OBJECT-TYPE
        SYNTAX IsisISLevel
        MAX-ACCESS not-accessible
        STATUS current
    ::= { isisPacketCounterEntry 1 }

    isisPacketCountDirection OBJECT-TYPE
        SYNTAX INTEGER
            {
                sending(1),
                receiving(2)
            }
        MAX-ACCESS not-accessible
        STATUS current
    ::= { isisPacketCounterEntry 2 }

    isisPacketCountIIHello OBJECT-TYPE





        SYNTAX Counter32
        UNITS "Number of IS-IS Hellos frames seen in this direction
              at this level"
        MAX-ACCESS read-only
        STATUS current
    ::= { isisPacketCounterEntry 3 }

    isisPacketCountISHello OBJECT-TYPE
        SYNTAX Counter32
        UNITS "Number of ES-IS frames seen in this direction at
             this level."
        MAX-ACCESS read-only
        STATUS current
    ::= { isisPacketCounterEntry 4 }

    isisPacketCountESHello OBJECT-TYPE
        SYNTAX Counter32
        UNITS "Number of ES Hello frames seen in this direction at
             this level"
        MAX-ACCESS read-only
        STATUS current
    ::= { isisPacketCounterEntry 5 }

    isisPacketCountLSP OBJECT-TYPE
        SYNTAX Counter32
        UNITS "Number of IS-IS LSP frames seen in this direction at
             this level"
        MAX-ACCESS read-only
        STATUS current
    ::= { isisPacketCounterEntry 6 }

    isisPacketCountCSNP OBJECT-TYPE
        SYNTAX Counter32
        UNITS "Number of IS-IS CSNP frames seen in this direction at
             this level"
        MAX-ACCESS read-only
        STATUS current
    ::= { isisPacketCounterEntry 7 }

    isisPacketCountPSNP OBJECT-TYPE
        SYNTAX Counter32
        UNITS "Number of IS-IS PSNP frames seen in this direction at
             this level"
        MAX-ACCESS read-only
        STATUS current
    ::= { isisPacketCounterEntry 8 }

    isisPacketCountUnknown OBJECT-TYPE
        SYNTAX Counter32
        UNITS "Number of unknown IS-IS frames seen at this level"
        MAX-ACCESS read-only
        STATUS current
    ::= { isisPacketCounterEntry 9 }


    isisISAdjTable OBJECT-TYPE
        SYNTAX SEQUENCE OF IsisISAdjEntry
        MAX-ACCESS not-accessible





        STATUS current
    ::= { isisISAdj 1 }

    isisISAdjEntry OBJECT-TYPE
        SYNTAX IsisISAdjEntry
        MAX-ACCESS not-accessible
        STATUS current
        INDEX { isisCircIndex,
                isisISAdjIndex }
    ::= { isisISAdjTable 1 }

    IsisISAdjEntry ::=
        SEQUENCE {
            isisISAdjIndex
                Unsigned32,
            isisISAdjState
                INTEGER,
            isisISAdj3WayState
                INTEGER,
            isisISAdjNeighSNPAAddress
                IsisOSINSAddress,
            isisISAdjNeighSysType
                INTEGER,
            isisISAdjNeighSysID
                IsisSystemID,
            isisISAdjNbrExtendedCircID
                Unsigned32,
            isisISAdjUsage
                IsisLevel,
            isisISAdjHoldTimer
                IsisUnsigned16TC,
            isisISAdjNeighPriority
                IsisISPriority,
            isisISAdjLastUpTime
                TimeStamp
      }

    isisISAdjIndex OBJECT-TYPE
        SYNTAX Unsigned32(1..4294967295)
        MAX-ACCESS not-accessible
        STATUS current





    ::= { isisISAdjEntry 1 }

    isisISAdjState OBJECT-TYPE
        SYNTAX INTEGER
            {
                 down (1),
                 initializing (2),
                 up (3),
                 failed(4)
            }
        MAX-ACCESS read-only
        STATUS current
    ::= { isisISAdjEntry 2 }

    isisISAdj3WayState OBJECT-TYPE
        SYNTAX INTEGER
            {
                 up (0),
                 initializing (1),
                 down (2),
                 failed (3)
            }
        MAX-ACCESS read-only
        STATUS current
    ::= { isisISAdjEntry 3 }

    isisISAdjNeighSNPAAddress OBJECT-TYPE
        SYNTAX IsisOSINSAddress
        MAX-ACCESS read-only
        STATUS current
    ::= { isisISAdjEntry 4 }





    isisISAdjNeighSysType OBJECT-TYPE
        SYNTAX INTEGER
            {
                l1IntermediateSystem(1),
                l2IntermediateSystem(2),
                l1L2IntermediateSystem(3),
                unknown(4)
            }
        MAX-ACCESS read-only
        STATUS current
    ::= { isisISAdjEntry 5 }

    isisISAdjNeighSysID OBJECT-TYPE
        SYNTAX IsisSystemID
        MAX-ACCESS read-only
        STATUS current
    ::= { isisISAdjEntry 6 }

    isisISAdjNbrExtendedCircID OBJECT-TYPE
        SYNTAX Unsigned32
        MAX-ACCESS read-only
        STATUS current
    ::= { isisISAdjEntry 7 }

    isisISAdjUsage OBJECT-TYPE
        SYNTAX IsisLevel
        MAX-ACCESS read-only
        STATUS current
    ::= { isisISAdjEntry 8 }

    isisISAdjHoldTimer OBJECT-TYPE
        SYNTAX IsisUnsigned16TC (1..65535)





        UNITS "seconds"
        MAX-ACCESS read-only
        STATUS current
    ::= { isisISAdjEntry 9 }

    isisISAdjNeighPriority OBJECT-TYPE
        SYNTAX IsisISPriority
        MAX-ACCESS read-only
        STATUS current
    ::= { isisISAdjEntry 10 }

    isisISAdjLastUpTime OBJECT-TYPE
        SYNTAX TimeStamp
        MAX-ACCESS read-only
        STATUS current
    ::= { isisISAdjEntry 11 }



    isisISAdjAreaAddrTable OBJECT-TYPE
        SYNTAX SEQUENCE OF IsisISAdjAreaAddrEntry
        MAX-ACCESS not-accessible
        STATUS current
    ::= { isisISAdj 2 }






    isisISAdjAreaAddrEntry OBJECT-TYPE
        SYNTAX IsisISAdjAreaAddrEntry
        MAX-ACCESS not-accessible
        STATUS current
        INDEX { isisCircIndex,
                isisISAdjIndex,
                isisISAdjAreaAddrIndex }
    ::= { isisISAdjAreaAddrTable 1 }

    IsisISAdjAreaAddrEntry ::=
        SEQUENCE {
            isisISAdjAreaAddrIndex
                Unsigned32,
            isisISAdjAreaAddress
                IsisOSINSAddress
            }

    isisISAdjAreaAddrIndex OBJECT-TYPE
        SYNTAX Unsigned32(1..4294967295)
        MAX-ACCESS not-accessible
        STATUS current
    ::= { isisISAdjAreaAddrEntry 1 }

    isisISAdjAreaAddress OBJECT-TYPE
        SYNTAX IsisOSINSAddress
        MAX-ACCESS read-only
        STATUS current
    ::= { isisISAdjAreaAddrEntry 2 }



    isisISAdjIPAddrTable OBJECT-TYPE
        SYNTAX SEQUENCE OF IsisISAdjIPAddrEntry





        MAX-ACCESS not-accessible
        STATUS current
    ::= { isisISAdj 3 }

    isisISAdjIPAddrEntry OBJECT-TYPE
        SYNTAX IsisISAdjIPAddrEntry
        MAX-ACCESS not-accessible
        STATUS current
        INDEX { isisCircIndex,
                isisISAdjIndex,
                isisISAdjIPAddrIndex
                }
    ::= { isisISAdjIPAddrTable 1 }

    IsisISAdjIPAddrEntry ::=
        SEQUENCE {
            isisISAdjIPAddrIndex
                Unsigned32,
            isisISAdjIPAddrType
                 InetAddressType,
            isisISAdjIPAddrAddress
                InetAddress
        }

    isisISAdjIPAddrIndex OBJECT-TYPE
        SYNTAX Unsigned32(1..4294967295)
        MAX-ACCESS not-accessible
        STATUS current
    ::= { isisISAdjIPAddrEntry 1 }

    isisISAdjIPAddrType OBJECT-TYPE
        SYNTAX InetAddressType
        MAX-ACCESS read-only
        STATUS current
    ::= { isisISAdjIPAddrEntry 2 }

    isisISAdjIPAddrAddress OBJECT-TYPE
        SYNTAX InetAddress
        MAX-ACCESS read-only
        STATUS current
    ::= { isisISAdjIPAddrEntry 3 }


    isisISAdjProtSuppTable OBJECT-TYPE
        SYNTAX SEQUENCE OF IsisISAdjProtSuppEntry
        MAX-ACCESS not-accessible
        STATUS current
    ::= { isisISAdj 4 }

    isisISAdjProtSuppEntry OBJECT-TYPE
        SYNTAX IsisISAdjProtSuppEntry
        MAX-ACCESS not-accessible
        STATUS current
        INDEX {  isisCircIndex,
                 isisISAdjIndex,
                 isisISAdjProtSuppProtocol }
    ::= { isisISAdjProtSuppTable 1 }

    IsisISAdjProtSuppEntry ::=
        SEQUENCE {





            isisISAdjProtSuppProtocol
                IsisSupportedProtocol
        }

    isisISAdjProtSuppProtocol OBJECT-TYPE
        SYNTAX IsisSupportedProtocol
        MAX-ACCESS read-only
        STATUS current
    ::= { isisISAdjProtSuppEntry 1 }


    isisRATable OBJECT-TYPE
        SYNTAX SEQUENCE OF IsisRAEntry
        MAX-ACCESS not-accessible
        STATUS current
    ::= { isisReachAddr 1 }

    isisRAEntry OBJECT-TYPE
        SYNTAX IsisRAEntry
        MAX-ACCESS not-accessible
        STATUS current
        INDEX { isisCircIndex,
                isisRAIndex }
    ::= { isisRATable 1 }

    IsisRAEntry ::=
        SEQUENCE {
            isisRAIndex
                Unsigned32,
            isisRAExistState
                RowStatus,





            isisRAAdminState
                IsisAdminState,
            isisRAAddrPrefix
                IsisOSINSAddress,
            isisRAMapType
                INTEGER,
            isisRAMetric
                IsisDefaultMetric,
            isisRAMetricType
                IsisMetricType,
            isisRASNPAAddress
                IsisOSINSAddress,
            isisRASNPAMask
                IsisOSINSAddress,
            isisRASNPAPrefix
                IsisOSINSAddress,
            isisRAType
                INTEGER
        }

    isisRAIndex OBJECT-TYPE
        SYNTAX Unsigned32(1..4294967295)
        MAX-ACCESS not-accessible
        STATUS current
    ::= { isisRAEntry 1 }

    isisRAExistState OBJECT-TYPE
        SYNTAX RowStatus
        MAX-ACCESS read-create
        STATUS current
    ::= { isisRAEntry 2 }

    isisRAAdminState OBJECT-TYPE
        SYNTAX IsisAdminState
        MAX-ACCESS read-create
        STATUS current
        DEFVAL { off }
    ::= { isisRAEntry 3 }

    isisRAAddrPrefix OBJECT-TYPE
        SYNTAX IsisOSINSAddress
        MAX-ACCESS read-create
        STATUS current
    ::= { isisRAEntry 4 }

    isisRAMapType OBJECT-TYPE
        SYNTAX INTEGER
            {
                none (1),
                explicit (2),
                extractIDI (3),
                extractDSP (4)
            }
        MAX-ACCESS read-create
        STATUS current

    ::= { isisRAEntry 5 }

    isisRAMetric OBJECT-TYPE
        SYNTAX IsisDefaultMetric
        MAX-ACCESS read-create
        STATUS current
        DEFVAL { 20 }
    ::= { isisRAEntry 6 }

    isisRAMetricType OBJECT-TYPE
        SYNTAX IsisMetricType
        MAX-ACCESS read-create
        STATUS current
        DEFVAL { internal }
    ::= { isisRAEntry 7 }

    isisRASNPAAddress OBJECT-TYPE
        SYNTAX IsisOSINSAddress
        MAX-ACCESS read-create
        STATUS current
        DEFVAL { ''H }
    ::= { isisRAEntry 8 }

    isisRASNPAMask OBJECT-TYPE
        SYNTAX IsisOSINSAddress
        MAX-ACCESS read-create
        STATUS current
        DEFVAL { '00'H }
    ::= { isisRAEntry 9 }

    isisRASNPAPrefix OBJECT-TYPE
        SYNTAX IsisOSINSAddress
        MAX-ACCESS read-create
        STATUS current
        DEFVAL { '00'H }
    ::= { isisRAEntry 10 }

    isisRAType OBJECT-TYPE
        SYNTAX INTEGER
            {
                manual (1),
                automatic (2)
            }





        MAX-ACCESS read-create
        STATUS current
        DEFVAL {manual}
    ::= {isisRAEntry 11 }




    isisIPRATable OBJECT-TYPE
        SYNTAX SEQUENCE OF IsisIPRAEntry
        MAX-ACCESS not-accessible
        STATUS current
    ::= { isisIPReachAddr 1 }

    isisIPRAEntry OBJECT-TYPE
        SYNTAX IsisIPRAEntry
        MAX-ACCESS not-accessible
        STATUS current
        INDEX {  isisSysLevelIndex,
                 isisIPRADestType,
                 isisIPRADest,
                 isisIPRADestPrefixLen,
                 isisIPRANextHopIndex }
    ::= { isisIPRATable 1 }

    IsisIPRAEntry ::=
        SEQUENCE {
            isisIPRADestType
                InetAddressType,
            isisIPRADest
                InetAddress,
            isisIPRADestPrefixLen
                InetAddressPrefixLength,
            isisIPRANextHopIndex
                Unsigned32,
            isisIPRANextHopType
                InetAddressType,
            isisIPRANextHop
                InetAddress,
            isisIPRAType
                INTEGER,
            isisIPRAExistState
                RowStatus,
            isisIPRAAdminState
                IsisAdminState,
            isisIPRAMetric
                IsisDefaultMetric,
            isisIPRAMetricType
                IsisMetricType,
            isisIPRAFullMetric
                IsisFullMetric,
            isisIPRASNPAAddress
                IsisOSINSAddress,
            isisIPRASourceType
                INTEGER
        }

    isisIPRADestType OBJECT-TYPE
        SYNTAX InetAddressType
        MAX-ACCESS not-accessible
        STATUS current
    ::= { isisIPRAEntry 1 }






    isisIPRADest OBJECT-TYPE
        SYNTAX InetAddress
        MAX-ACCESS not-accessible
        STATUS current

    ::= { isisIPRAEntry 2 }

    isisIPRADestPrefixLen OBJECT-TYPE
        SYNTAX InetAddressPrefixLength
        MAX-ACCESS not-accessible
        STATUS current
    ::= { isisIPRAEntry 3 }

    isisIPRANextHopIndex OBJECT-TYPE
        SYNTAX Unsigned32(1..4294967295)
        MAX-ACCESS not-accessible
        STATUS current
    ::= { isisIPRAEntry 4 }

    isisIPRANextHopType OBJECT-TYPE
        SYNTAX InetAddressType
        MAX-ACCESS read-create
        STATUS current
    ::= { isisIPRAEntry 5 }





    isisIPRANextHop OBJECT-TYPE
        SYNTAX InetAddress
        MAX-ACCESS read-create
        STATUS current
    ::= { isisIPRAEntry 6 }

    isisIPRAType OBJECT-TYPE
        SYNTAX INTEGER
            {
                manual (1),
                automatic (2)
            }
        MAX-ACCESS read-create
        STATUS current
    ::= { isisIPRAEntry 7 }

    isisIPRAExistState OBJECT-TYPE
        SYNTAX RowStatus
        MAX-ACCESS read-create
        STATUS current
    ::= { isisIPRAEntry 8 }

    isisIPRAAdminState OBJECT-TYPE
        SYNTAX IsisAdminState
        MAX-ACCESS read-create
        STATUS current
        DEFVAL { off }
    ::= { isisIPRAEntry 9 }

    isisIPRAMetric OBJECT-TYPE
        SYNTAX IsisDefaultMetric
        MAX-ACCESS read-create
        STATUS current
        DEFVAL { 10 }
    ::= { isisIPRAEntry 10 }

    isisIPRAMetricType OBJECT-TYPE
        SYNTAX IsisMetricType
        MAX-ACCESS read-create
        STATUS current
        DEFVAL { internal }
    ::= { isisIPRAEntry 11 }

    isisIPRAFullMetric OBJECT-TYPE
        SYNTAX IsisFullMetric
        MAX-ACCESS read-create
        STATUS current
        DEFVAL { 10 }
    ::= { isisIPRAEntry 12 }

    isisIPRASNPAAddress OBJECT-TYPE
        SYNTAX IsisOSINSAddress
        MAX-ACCESS read-create
        STATUS current
        DEFVAL { ''H }
    ::= { isisIPRAEntry 13 }





    isisIPRASourceType OBJECT-TYPE
        SYNTAX INTEGER
            {
                static (1),
                direct (2),
                ospfv2 (3),
                ospfv3 (4),
                isis   (5),
                rip    (6),
                igrp   (7),
                eigrp  (8),
                bgp    (9),
                other (10)
            }
        MAX-ACCESS read-only
        STATUS current
    ::= { isisIPRAEntry 14 }


    isisLSPSummaryTable OBJECT-TYPE
        SYNTAX SEQUENCE OF IsisLSPSummaryEntry
        MAX-ACCESS not-accessible
        STATUS current
    ::= { isisLSPDataBase 1 }

    isisLSPSummaryEntry OBJECT-TYPE
        SYNTAX IsisLSPSummaryEntry
        MAX-ACCESS not-accessible
        STATUS current
        INDEX {  isisLSPLevel,
                 isisLSPID }
    ::= { isisLSPSummaryTable 1 }

    IsisLSPSummaryEntry ::=





        SEQUENCE {
            isisLSPLevel
                IsisISLevel,
            isisLSPID
                IsisLinkStatePDUID,
            isisLSPSeq
                Unsigned32,
            isisLSPZeroLife
                TruthValue,
            isisLSPChecksum
                IsisUnsigned16TC,
            isisLSPLifetimeRemain
                IsisUnsigned16TC,
            isisLSPPDULength
                IsisUnsigned16TC,
            isisLSPAttributes
                IsisUnsigned8TC
        }

    isisLSPLevel OBJECT-TYPE
        SYNTAX IsisISLevel
        MAX-ACCESS not-accessible
        STATUS current
    ::= { isisLSPSummaryEntry 1 }

    isisLSPID OBJECT-TYPE
        SYNTAX IsisLinkStatePDUID
        MAX-ACCESS not-accessible
        STATUS current
    ::= { isisLSPSummaryEntry 2 }

    isisLSPSeq OBJECT-TYPE
        SYNTAX Unsigned32
        MAX-ACCESS read-only
        STATUS current
    ::= { isisLSPSummaryEntry 3 }

    isisLSPZeroLife OBJECT-TYPE
        SYNTAX TruthValue
        MAX-ACCESS read-only
        STATUS current
    ::= { isisLSPSummaryEntry 4 }

    isisLSPChecksum OBJECT-TYPE
        SYNTAX IsisUnsigned16TC
        MAX-ACCESS read-only
        STATUS current
    ::= { isisLSPSummaryEntry 5 }

    isisLSPLifetimeRemain OBJECT-TYPE
        SYNTAX IsisUnsigned16TC
        UNITS "seconds"
        MAX-ACCESS read-only
        STATUS current
    ::= { isisLSPSummaryEntry 6 }

    isisLSPPDULength OBJECT-TYPE
        SYNTAX IsisUnsigned16TC
        MAX-ACCESS read-only
        STATUS current
    ::= { isisLSPSummaryEntry 7 }

    isisLSPAttributes OBJECT-TYPE
        SYNTAX IsisUnsigned8TC
        MAX-ACCESS read-only
        STATUS current
    ::= { isisLSPSummaryEntry 8 }


    isisLSPTLVTable OBJECT-TYPE
        SYNTAX SEQUENCE OF IsisLSPTLVEntry
        MAX-ACCESS not-accessible
        STATUS current





    ::= { isisLSPDataBase 2 }

    isisLSPTLVEntry OBJECT-TYPE
        SYNTAX IsisLSPTLVEntry
        MAX-ACCESS not-accessible
        STATUS current
        INDEX {  isisLSPLevel,
                 isisLSPID,
                 isisLSPTLVIndex }
    ::= { isisLSPTLVTable 1 }

    IsisLSPTLVEntry ::=
        SEQUENCE {
            isisLSPTLVIndex
                Unsigned32,
            isisLSPTLVSeq
                Unsigned32,
            isisLSPTLVChecksum
                IsisUnsigned16TC,
            isisLSPTLVType
                IsisUnsigned8TC,
            isisLSPTLVLen
                IsisUnsigned8TC,
            isisLSPTLVValue
                OCTET STRING
        }

    isisLSPTLVIndex OBJECT-TYPE
        SYNTAX Unsigned32(1..4294967295)
        MAX-ACCESS not-accessible
        STATUS current
    ::= { isisLSPTLVEntry 1 }

    isisLSPTLVSeq OBJECT-TYPE
        SYNTAX Unsigned32
        MAX-ACCESS read-only
        STATUS current





    ::= { isisLSPTLVEntry 2 }

    isisLSPTLVChecksum OBJECT-TYPE
        SYNTAX IsisUnsigned16TC
        MAX-ACCESS read-only
        STATUS current
    ::= { isisLSPTLVEntry 3 }

    isisLSPTLVType OBJECT-TYPE
        SYNTAX IsisUnsigned8TC
        MAX-ACCESS read-only
        STATUS current
    ::= { isisLSPTLVEntry 4 }

    isisLSPTLVLen OBJECT-TYPE
        SYNTAX IsisUnsigned8TC
        MAX-ACCESS read-only
        STATUS current
    ::= { isisLSPTLVEntry 5 }

    isisLSPTLVValue OBJECT-TYPE
        SYNTAX OCTET STRING (SIZE(0..255))
        MAX-ACCESS read-only
        STATUS current
    ::= { isisLSPTLVEntry 6 }




    isisNotificationEntry OBJECT IDENTIFIER
        ::= { isisNotification 1 }

    isisNotificationSysLevelIndex OBJECT-TYPE
        SYNTAX IsisLevel
        MAX-ACCESS accessible-for-notify





        STATUS current
    ::= { isisNotificationEntry 1 }

    isisNotificationCircIfIndex OBJECT-TYPE
        SYNTAX Unsigned32 (1..2147483647)
        MAX-ACCESS accessible-for-notify
        STATUS current
    ::= { isisNotificationEntry 2 }

    isisPduLspId OBJECT-TYPE
        SYNTAX IsisLinkStatePDUID
        MAX-ACCESS accessible-for-notify
        STATUS current
    ::= { isisNotificationEntry 3 }

    isisPduFragment OBJECT-TYPE
        SYNTAX IsisPDUHeader
        MAX-ACCESS accessible-for-notify
        STATUS current
    ::= { isisNotificationEntry 4 }

    isisPduFieldLen OBJECT-TYPE
        SYNTAX IsisUnsigned8TC
        MAX-ACCESS accessible-for-notify
        STATUS current
    ::= { isisNotificationEntry 5 }

    isisPduMaxAreaAddress OBJECT-TYPE
        SYNTAX IsisUnsigned8TC
        MAX-ACCESS accessible-for-notify
        STATUS current
    ::= { isisNotificationEntry 6 }





    isisPduProtocolVersion OBJECT-TYPE
        SYNTAX IsisUnsigned8TC
        MAX-ACCESS accessible-for-notify
        STATUS current
    ::= { isisNotificationEntry 7 }

    isisPduLspSize OBJECT-TYPE
        SYNTAX Unsigned32 (0..2147483647)
        MAX-ACCESS accessible-for-notify
        STATUS current
    ::= { isisNotificationEntry 8 }

    isisPduOriginatingBufferSize OBJECT-TYPE
        SYNTAX IsisUnsigned16TC (0..16000)
        MAX-ACCESS accessible-for-notify
        STATUS current
    ::= { isisNotificationEntry 9 }

    isisPduBufferSize OBJECT-TYPE
        SYNTAX IsisUnsigned16TC (0..16000)
        MAX-ACCESS accessible-for-notify
        STATUS current
    ::= { isisNotificationEntry 10 }

    isisPduProtocolsSupported OBJECT-TYPE
        SYNTAX OCTET STRING (SIZE(0..255))
        MAX-ACCESS accessible-for-notify
        STATUS current
    ::= { isisNotificationEntry 11 }

    isisAdjState OBJECT-TYPE
        SYNTAX INTEGER
            {





                 down (1),
                 initializing (2),
                 up (3),
                 failed(4)
            }
        MAX-ACCESS accessible-for-notify
        STATUS current
    ::= { isisNotificationEntry 12 }

    isisErrorOffset OBJECT-TYPE
        SYNTAX Unsigned32
        MAX-ACCESS accessible-for-notify
        STATUS current
    ::= { isisNotificationEntry 13 }

    isisErrorTLVType OBJECT-TYPE
        SYNTAX Unsigned32 (0..255)
        MAX-ACCESS accessible-for-notify
        STATUS current
    ::= { isisNotificationEntry 14 }

    isisNotificationAreaAddress OBJECT-TYPE
        SYNTAX IsisOSINSAddress
        MAX-ACCESS accessible-for-notify
        STATUS current
    ::= { isisNotificationEntry 15 }


    isisDatabaseOverload NOTIFICATION-TYPE
        OBJECTS {
            isisNotificationSysLevelIndex,
            isisSysLevelState
        }





        STATUS current
    ::= { isisNotifications 1 }

    isisManualAddressDrops NOTIFICATION-TYPE
        OBJECTS {
            isisNotificationAreaAddress
        }
        STATUS current
    ::= { isisNotifications 2 }

    isisCorruptedLSPDetected NOTIFICATION-TYPE
        OBJECTS {
            isisNotificationSysLevelIndex,
            isisPduLspId
        }
        STATUS current






    ::= { isisNotifications 3 }

    isisAttemptToExceedMaxSequence NOTIFICATION-TYPE
        OBJECTS {
            isisNotificationSysLevelIndex,
            isisPduLspId
        }
        STATUS current

    ::= { isisNotifications 4 }

    isisIDLenMismatch  NOTIFICATION-TYPE
        OBJECTS {
            isisNotificationSysLevelIndex,
            isisPduFieldLen,
            isisNotificationCircIfIndex,
            isisPduFragment
        }
        STATUS current

    ::= { isisNotifications 5 }

    isisMaxAreaAddressesMismatch NOTIFICATION-TYPE
        OBJECTS {





            isisNotificationSysLevelIndex,
            isisPduMaxAreaAddress,
            isisNotificationCircIfIndex,
            isisPduFragment
        }

        STATUS current

    ::= { isisNotifications 6 }

    isisOwnLSPPurge NOTIFICATION-TYPE
        OBJECTS {
            isisNotificationSysLevelIndex,
            isisNotificationCircIfIndex,
            isisPduLspId
        }
        STATUS current

    ::= { isisNotifications 7 }

    isisSequenceNumberSkip NOTIFICATION-TYPE
        OBJECTS {
            isisNotificationSysLevelIndex,
            isisNotificationCircIfIndex,
            isisPduLspId
        }
        STATUS current






    ::= { isisNotifications 8 }

    isisAuthenticationTypeFailure NOTIFICATION-TYPE
        OBJECTS {
            isisNotificationSysLevelIndex,
            isisNotificationCircIfIndex,
            isisPduFragment
        }
        STATUS current

    ::= { isisNotifications 9 }

    isisAuthenticationFailure NOTIFICATION-TYPE
        OBJECTS {
            isisNotificationSysLevelIndex,
            isisNotificationCircIfIndex,
            isisPduFragment
        }
        STATUS current

    ::= { isisNotifications 10 }

    isisVersionSkew NOTIFICATION-TYPE
        OBJECTS {
            isisNotificationSysLevelIndex,
            isisNotificationCircIfIndex,
            isisPduProtocolVersion,
            isisPduFragment
        }
        STATUS current

    ::= { isisNotifications 11 }

    isisAreaMismatch NOTIFICATION-TYPE
        OBJECTS {
            isisNotificationCircIfIndex,
            isisPduFragment
        }
        STATUS current

    ::= { isisNotifications 12 }

    isisRejectedAdjacency NOTIFICATION-TYPE
        OBJECTS {
            isisNotificationSysLevelIndex,
            isisNotificationCircIfIndex,
            isisPduFragment
        }
        STATUS current

    ::= { isisNotifications 13 }

    isisLSPTooLargeToPropagate NOTIFICATION-TYPE
        OBJECTS {
            isisNotificationSysLevelIndex,
            isisNotificationCircIfIndex,
            isisPduLspSize,
            isisPduLspId
        }
        STATUS current

    ::= { isisNotifications 14 }

    isisOrigLSPBuffSizeMismatch NOTIFICATION-TYPE
        OBJECTS {
            isisNotificationSysLevelIndex,
            isisNotificationCircIfIndex,
            isisPduLspId,
            isisPduOriginatingBufferSize,
            isisPduBufferSize
        }
        STATUS current

    ::= { isisNotifications 15 }

    isisProtocolsSupportedMismatch NOTIFICATION-TYPE
        OBJECTS {
            isisNotificationSysLevelIndex,
            isisNotificationCircIfIndex,
            isisPduProtocolsSupported,
            isisPduLspId,
            isisPduFragment
        }
        STATUS current

    ::= { isisNotifications 16 }

    isisAdjacencyChange NOTIFICATION-TYPE
        OBJECTS {
            isisNotificationSysLevelIndex,
            isisNotificationCircIfIndex,
            isisPduLspId,
            isisAdjState
        }
        STATUS current

    ::= { isisNotifications 17 }

    isisLSPErrorDetected NOTIFICATION-TYPE
        OBJECTS {
            isisNotificationSysLevelIndex,
            isisPduLspId,
            isisNotificationCircIfIndex,
            isisPduFragment,
            isisErrorOffset,
            isisErrorTLVType
        }
        STATUS current

    ::= { isisNotifications 18 }


isisCompliances OBJECT IDENTIFIER ::= { isisConformance 1 }
isisGroups      OBJECT IDENTIFIER ::= { isisConformance 2 }


    isisCompliance MODULE-COMPLIANCE
        STATUS current





        MODULE -- this module
            MANDATORY-GROUPS {
                    isisSystemGroup,
                    isisCircuitGroup,
                    isisISAdjGroup,
                    isisNotificationObjectGroup,
                    isisNotificationGroup
            }
    ::= { isisCompliances 1 }

    isisAdvancedCompliance MODULE-COMPLIANCE
        STATUS current





        MODULE -- this module
            MANDATORY-GROUPS {
                    isisSystemGroup,
                    isisCircuitGroup,
                    isisISAdjGroup,
                    isisNotificationObjectGroup,
                    isisNotificationGroup,
                    isisISPDUCounterGroup,
                    isisRATableGroup,
                    isisISIPRADestGroup,
                    isisLSPGroup
            }
    ::= { isisCompliances 2 }

    isisReadOnlyCompliance MODULE-COMPLIANCE
       STATUS     current
       MODULE -- this module
            MANDATORY-GROUPS {
                    isisSystemGroup,
                    isisCircuitGroup,
                    isisISAdjGroup
            }

       OBJECT isisSysLevelType
       MIN-ACCESS read-only

       OBJECT isisSysID
       MIN-ACCESS read-only

       OBJECT isisSysMaxPathSplits
       MIN-ACCESS read-only

       OBJECT isisSysMaxLSPGenInt
       MIN-ACCESS read-only

       OBJECT isisSysPollESHelloRate
       MIN-ACCESS read-only

       OBJECT isisSysWaitTime
       MIN-ACCESS read-only

       OBJECT isisSysAdminState
       MIN-ACCESS read-only

       OBJECT isisSysL2toL1Leaking
       MIN-ACCESS read-only






       OBJECT isisSysMaxAge
       MIN-ACCESS read-only

       OBJECT isisManAreaAddrExistState
       MIN-ACCESS read-only

       OBJECT isisSysLevelOrigLSPBuffSize
       MIN-ACCESS read-only

       OBJECT isisSysLevelMinLSPGenInt
       MIN-ACCESS read-only

       OBJECT isisSysLevelSetOverload
       MIN-ACCESS read-only

       OBJECT isisSysLevelSetOverloadUntil
       MIN-ACCESS read-only

       OBJECT isisSysLevelMetricStyle
       MIN-ACCESS read-only

       OBJECT isisSysLevelSPFConsiders
       MIN-ACCESS read-only

       OBJECT isisSysLevelTEEnabled
       MIN-ACCESS read-only

       OBJECT isisSysReceiveLSPBufferSize
       MIN-ACCESS read-only

       OBJECT isisSummAddrExistState
       MIN-ACCESS read-only

       OBJECT isisSummAddrMetric
       MIN-ACCESS read-only

       OBJECT isisSummAddrFullMetric
       MIN-ACCESS read-only

       OBJECT isisRedistributeAddrExistState
       MIN-ACCESS read-only

       OBJECT isisCircAdminState
       MIN-ACCESS read-only

       OBJECT isisCircExistState
       MIN-ACCESS read-only

       OBJECT isisCircType
       MIN-ACCESS read-only

       OBJECT isisCircExtDomain
       MIN-ACCESS read-only

       OBJECT isisCircLevelType
       MIN-ACCESS read-only

       OBJECT isisCircPassiveCircuit





       MIN-ACCESS read-only

       OBJECT isisCircMeshGroupEnabled
       MIN-ACCESS read-only

       OBJECT isisCircMeshGroup
       MIN-ACCESS read-only

       OBJECT isisCircSmallHellos
       MIN-ACCESS read-only

       OBJECT isisCircExtendedCircID
       MIN-ACCESS read-only

       OBJECT isisCircIfIndex
       MIN-ACCESS read-only

       OBJECT isisCirc3WayEnabled
       MIN-ACCESS read-only

       OBJECT isisCircLevelMetric
       MIN-ACCESS read-only

       OBJECT isisCircLevelWideMetric
       MIN-ACCESS read-only

       OBJECT isisCircLevelISPriority
       MIN-ACCESS read-only





       OBJECT isisCircLevelHelloMultiplier
       MIN-ACCESS read-only

       OBJECT isisCircLevelHelloTimer
       MIN-ACCESS read-only

       OBJECT isisCircLevelDRHelloTimer
       MIN-ACCESS read-only

       OBJECT isisCircLevelLSPThrottle
       MIN-ACCESS read-only

       OBJECT isisCircLevelMinLSPRetransInt
       MIN-ACCESS read-only

       OBJECT isisCircLevelCSNPInterval
       MIN-ACCESS read-only

       OBJECT isisCircLevelPartSNPInterval
       MIN-ACCESS read-only

    ::= { isisCompliances 3 }


    isisSystemGroup OBJECT-GROUP
        OBJECTS {
            isisSysVersion,
            isisSysLevelType,
            isisSysID,
            isisSysMaxPathSplits,
            isisSysMaxLSPGenInt,
            isisSysPollESHelloRate,
            isisSysWaitTime,





            isisSysAdminState,
            isisSysL2toL1Leaking,
            isisSysMaxAge,
            isisSysProtSupported,
            isisSysNotificationEnable,
            isisManAreaAddrExistState,
            isisSysLevelOrigLSPBuffSize,
            isisSysLevelMinLSPGenInt,
            isisSysLevelState,
            isisSysLevelSetOverload,
            isisSysLevelSetOverloadUntil,
            isisSysLevelMetricStyle,
            isisSysLevelSPFConsiders,
            isisSysLevelTEEnabled,
            isisSysReceiveLSPBufferSize,
            isisSummAddrExistState,
            isisSummAddrMetric,
            isisAreaAddr,
            isisSummAddrFullMetric,
            isisRedistributeAddrExistState,
            isisRouterHostName,
            isisRouterID,
            isisSysStatCorrLSPs,
            isisSysStatLSPDbaseOloads,
            isisSysStatManAddrDropFromAreas,
            isisSysStatAttmptToExMaxSeqNums,
            isisSysStatSeqNumSkips,
            isisSysStatOwnLSPPurges,
            isisSysStatIDFieldLenMismatches,
            isisSysStatPartChanges,
            isisSysStatSPFRuns,
            isisSysStatAuthTypeFails,
            isisSysStatAuthFails,
            isisSysStatLSPErrors
        }
        STATUS current
    ::= { isisGroups 1 }

    isisCircuitGroup OBJECT-GROUP
        OBJECTS {
            isisNextCircIndex,
            isisCircAdminState,
            isisCircExistState,
            isisCircType,
            isisCircExtDomain,





            isisCircLevelType,
            isisCircAdjChanges,
            isisCircNumAdj,
            isisCircInitFails,
            isisCircRejAdjs,
            isisCircIDFieldLenMismatches,
            isisCircMaxAreaAddrMismatches,
            isisCircAuthTypeFails,
            isisCircAuthFails,
            isisCircLANDesISChanges,
            isisCircPassiveCircuit,
            isisCircMeshGroupEnabled,
            isisCircMeshGroup,
            isisCircSmallHellos,
            isisCircLastUpTime,
            isisCirc3WayEnabled,
            isisCircExtendedCircID,
            isisCircIfIndex,
            isisCircLevelMetric,
            isisCircLevelWideMetric,
            isisCircLevelISPriority,
            isisCircLevelIDOctet,
            isisCircLevelID,
            isisCircLevelDesIS,
            isisCircLevelHelloMultiplier,
            isisCircLevelHelloTimer,
            isisCircLevelDRHelloTimer,
            isisCircLevelLSPThrottle,
            isisCircLevelMinLSPRetransInt,
            isisCircLevelCSNPInterval,
            isisCircLevelPartSNPInterval
        }
        STATUS current
    ::= { isisGroups 2 }

    isisISAdjGroup OBJECT-GROUP
        OBJECTS {
            isisISAdjState,
            isisISAdj3WayState,
            isisISAdjNeighSNPAAddress,
            isisISAdjNeighSysType,
            isisISAdjNeighSysID,
            isisISAdjNbrExtendedCircID,
            isisISAdjUsage,
            isisISAdjHoldTimer,





            isisISAdjNeighPriority,
            isisISAdjLastUpTime,
            isisISAdjAreaAddress,
            isisISAdjIPAddrType,
            isisISAdjIPAddrAddress,
            isisISAdjProtSuppProtocol
        }
        STATUS current
    ::= { isisGroups 3 }

    isisNotificationObjectGroup OBJECT-GROUP
        OBJECTS {
            isisNotificationSysLevelIndex,
            isisNotificationCircIfIndex,
            isisPduLspId,
            isisPduFragment,
            isisPduFieldLen,
            isisPduMaxAreaAddress,
            isisPduProtocolVersion,
            isisPduLspSize,
            isisPduOriginatingBufferSize,
            isisPduBufferSize,
            isisPduProtocolsSupported,
            isisAdjState,
            isisErrorOffset,
            isisErrorTLVType,
            isisNotificationAreaAddress
        }
        STATUS current
    ::= { isisGroups 4 }


    isisNotificationGroup        NOTIFICATION-GROUP
        NOTIFICATIONS {
            isisDatabaseOverload,
            isisManualAddressDrops,
            isisCorruptedLSPDetected,
            isisAttemptToExceedMaxSequence,
            isisIDLenMismatch,
            isisMaxAreaAddressesMismatch,
            isisOwnLSPPurge,
            isisSequenceNumberSkip,
            isisAuthenticationTypeFailure,





            isisAuthenticationFailure,
            isisVersionSkew,
            isisAreaMismatch,
            isisRejectedAdjacency,
            isisLSPTooLargeToPropagate,
            isisOrigLSPBuffSizeMismatch,
            isisProtocolsSupportedMismatch,
            isisAdjacencyChange,
            isisLSPErrorDetected
        }
        STATUS current
    ::= { isisGroups 5 }


    isisISPDUCounterGroup OBJECT-GROUP
        OBJECTS {
            isisPacketCountIIHello,
            isisPacketCountISHello,
            isisPacketCountESHello,
            isisPacketCountLSP,
            isisPacketCountCSNP,
            isisPacketCountPSNP,
            isisPacketCountUnknown
        }
        STATUS current
    ::= { isisGroups 6 }


    isisRATableGroup OBJECT-GROUP
        OBJECTS {
            isisRAExistState,
            isisRAAdminState,
            isisRAAddrPrefix,
            isisRAMapType,
            isisRAMetric,
            isisRAMetricType,
            isisRASNPAAddress,
            isisRASNPAMask,
            isisRASNPAPrefix,
            isisRAType
        }
        STATUS current
    ::= { isisGroups 7 }


    isisISIPRADestGroup OBJECT-GROUP
        OBJECTS {
            isisIPRANextHopType,
            isisIPRANextHop,
            isisIPRAType,
            isisIPRAExistState,
            isisIPRAAdminState,
            isisIPRAMetric,
            isisIPRAFullMetric,
            isisIPRAMetricType,
            isisIPRASNPAAddress,
            isisIPRASourceType
        }
        STATUS current
    ::= { isisGroups 8 }

    isisLSPGroup OBJECT-GROUP
        OBJECTS {
            isisLSPSeq,
            isisLSPZeroLife,
            isisLSPChecksum,
            isisLSPLifetimeRemain,
            isisLSPPDULength,
            isisLSPAttributes,
            isisLSPTLVSeq,
            isisLSPTLVChecksum,
            isisLSPTLVType,
            isisLSPTLVLen,
            isisLSPTLVValue
        }
        STATUS current
    ::= { isisGroups 9 }

END
