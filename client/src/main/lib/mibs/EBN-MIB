EBN-MIB DEFINITIONS ::= BEGIN

   IMPORTS
           MODULE-IDENTITY, OBJECT-TYPE, Unsigned32
                       FROM SNMPv2-SMI
           MODULE-COMPLIANCE, OBJECT-GROUP
                       FROM SNMPv2-CONF
           DisplayString, TEXTUAL-CONVENTION
                       FROM SNMPv2-TC
           SnaControlPointName
                   FROM APPN-MIB
           snanauMIB
                   FROM SNA-NAU-MIB;

   ebnMIB   MODULE-IDENTITY
          LAST-UPDATED "9804281800Z" -- April 28, 1998
          ORGANIZATION  "IETF SNA NAU MIB WG / AIW APPN MIBs SIG"


          ::= { snanauMIB 7 }







   SnaNAUWildcardName   ::= TEXTUAL-CONVENTION
        STATUS current

   SYNTAX DisplayString(SIZE(1..17))

   ebnObjects              OBJECT IDENTIFIER ::= { ebnMIB 1 }


   ebnDir                  OBJECT IDENTIFIER ::= { ebnObjects 1 }

   ebnDirTable OBJECT-TYPE
        SYNTAX SEQUENCE OF EbnDirEntry
        MAX-ACCESS not-accessible
        STATUS current

        ::= { ebnDir 1 }

   ebnDirEntry OBJECT-TYPE
        SYNTAX EbnDirEntry
        MAX-ACCESS not-accessible





        STATUS current

        INDEX { ebnDirLuName }

        ::= { ebnDirTable 1 }

   EbnDirEntry ::= SEQUENCE {
           ebnDirLuName             SnaNAUWildcardName,
           ebnDirSubnetAffiliation  INTEGER     }

   ebnDirLuName OBJECT-TYPE
        SYNTAX SnaNAUWildcardName
        MAX-ACCESS not-accessible
        STATUS current

        ::= { ebnDirEntry 1 }

   ebnDirSubnetAffiliation OBJECT-TYPE
        SYNTAX INTEGER { native (1),
                         nonNative (2),
                         subarea (3) }
        MAX-ACCESS read-only
        STATUS current

        ::= { ebnDirEntry 2 }


   ebnIsRscv               OBJECT IDENTIFIER ::= { ebnObjects 2 }

   ebnIsRscvTable OBJECT-TYPE





        SYNTAX SEQUENCE OF EbnIsRscvEntry
        MAX-ACCESS not-accessible
        STATUS current

        ::= { ebnIsRscv 1}

   ebnIsRscvEntry OBJECT-TYPE
        SYNTAX EbnIsRscvEntry
        MAX-ACCESS not-accessible
        STATUS current
        INDEX { ebnIsRscvCpName,
                ebnIsRscvPcid }

        ::= { ebnIsRscvTable 1 }

   EbnIsRscvEntry ::= SEQUENCE {
           ebnIsRscvCpName            SnaControlPointName,
           ebnIsRscvPcid              OCTET STRING,
           ebnIsRscvDestinationRoute  OCTET STRING,
           ebnIsRscvDestinationCos    DisplayString }

   ebnIsRscvCpName OBJECT-TYPE
        SYNTAX SnaControlPointName
        MAX-ACCESS not-accessible
        STATUS current

        ::= { ebnIsRscvEntry 1 }






   ebnIsRscvPcid OBJECT-TYPE
        SYNTAX OCTET STRING (SIZE (8))
        MAX-ACCESS not-accessible
        STATUS current

        ::= { ebnIsRscvEntry 2 }

   ebnIsRscvDestinationRoute OBJECT-TYPE
        SYNTAX OCTET STRING(SIZE (0..255))
        MAX-ACCESS read-only

        STATUS current

        ::= { ebnIsRscvEntry 3 }

   ebnIsRscvDestinationCos OBJECT-TYPE
        SYNTAX DisplayString (SIZE (1..8))
        MAX-ACCESS read-only
        STATUS current

        ::= { ebnIsRscvEntry 4 }


   ebnDirConfig            OBJECT IDENTIFIER ::= { ebnObjects 3 }





   ebnSearchCacheTime    OBJECT-TYPE
        SYNTAX Unsigned32
        UNITS "minutes"
        MAX-ACCESS read-only
        STATUS current

        ::= { ebnDirConfig 1 }

   ebnMaxSearchCache OBJECT-TYPE
        SYNTAX Unsigned32
        UNITS "entries"
        MAX-ACCESS read-only
        STATUS current

        ::= { ebnDirConfig 2 }

   ebnDefaultSubnetVisitCount  OBJECT-TYPE
        SYNTAX Unsigned32
        UNITS "topology subnetworks"
        MAX-ACCESS read-only
        STATUS current

        ::= { ebnDirConfig 3 }







   ebnCOS                  OBJECT IDENTIFIER ::= { ebnObjects 4 }

   ebnCosMapTable OBJECT-TYPE
        SYNTAX SEQUENCE OF EbnCosMapEntry
        MAX-ACCESS not-accessible
        STATUS current

        ::= { ebnCOS 1 }

   ebnCosMapEntry OBJECT-TYPE
        SYNTAX EbnCosMapEntry
        MAX-ACCESS not-accessible
        STATUS current

        INDEX { ebnCosMapCpName,
                ebnCosMapNonNativeCos }

        ::= { ebnCosMapTable 1 }

   EbnCosMapEntry ::= SEQUENCE {
           ebnCosMapCpName              SnaNAUWildcardName,
           ebnCosMapNonNativeCos        DisplayString,
           ebnCosMapNativeCos           DisplayString }

   ebnCosMapCpName OBJECT-TYPE
        SYNTAX SnaNAUWildcardName
        MAX-ACCESS not-accessible
        STATUS current

        ::= { ebnCosMapEntry 1 }

   ebnCosMapNonNativeCos OBJECT-TYPE
        SYNTAX DisplayString (SIZE(1..8))





        MAX-ACCESS not-accessible
        STATUS current

        ::= { ebnCosMapEntry 2 }

   ebnCosMapNativeCos OBJECT-TYPE
        SYNTAX DisplayString (SIZE(1..8))
        MAX-ACCESS read-only
        STATUS current

        ::= { ebnCosMapEntry 3 }


   ebnSubnetRoutingList    OBJECT IDENTIFIER ::= { ebnObjects 5 }

   ebnSubnetSearchTable OBJECT-TYPE
        SYNTAX SEQUENCE OF EbnSubnetSearchEntry
        MAX-ACCESS not-accessible
        STATUS current

        ::= { ebnSubnetRoutingList 1 }

   ebnSubnetSearchEntry OBJECT-TYPE
        SYNTAX EbnSubnetSearchEntry
        MAX-ACCESS not-accessible
        STATUS current

        INDEX { ebnSubnetSearchLuName }

        ::= { ebnSubnetSearchTable 1 }

   EbnSubnetSearchEntry ::= SEQUENCE {
           ebnSubnetSearchLuName   SnaNAUWildcardName,
           ebnSubnetSearchDynamics INTEGER,
           ebnSubnetSearchOrdering INTEGER   }

   ebnSubnetSearchLuName OBJECT-TYPE
        SYNTAX SnaNAUWildcardName
        MAX-ACCESS not-accessible
        STATUS current

        ::= { ebnSubnetSearchEntry 1 }

   ebnSubnetSearchDynamics OBJECT-TYPE
        SYNTAX INTEGER { none(1),
                         limited (2),
                         full (3) }
        MAX-ACCESS read-only
        STATUS current

        ::= { ebnSubnetSearchEntry 2 }

   ebnSubnetSearchOrdering OBJECT-TYPE
        SYNTAX INTEGER{ priority(1),
                        defined(2) }
        MAX-ACCESS read-only
        STATUS current

        ::= { ebnSubnetSearchEntry 3 }


   ebnSearchTable OBJECT-TYPE
        SYNTAX SEQUENCE OF EbnSearchEntry
        MAX-ACCESS not-accessible
        STATUS current

        ::= { ebnSubnetRoutingList 2 }

   ebnSearchEntry OBJECT-TYPE
        SYNTAX EbnSearchEntry
        MAX-ACCESS not-accessible
        STATUS current

        INDEX { ebnSearchLuName,
                ebnSearchIndex }

        ::= { ebnSearchTable 1 }

   EbnSearchEntry ::= SEQUENCE {
           ebnSearchLuName  SnaNAUWildcardName,
           ebnSearchIndex   Unsigned32,
           ebnSearchCpName  DisplayString,
           ebnSearchSNVC    Unsigned32  }

   ebnSearchLuName OBJECT-TYPE
        SYNTAX SnaNAUWildcardName
        MAX-ACCESS not-accessible
        STATUS current

        ::= { ebnSearchEntry 1 }

   ebnSearchIndex OBJECT-TYPE
        SYNTAX Unsigned32
        MAX-ACCESS not-accessible
        STATUS current

        ::= { ebnSearchEntry 2 }

   ebnSearchCpName OBJECT-TYPE
        SYNTAX DisplayString(SIZE(1..17))
        MAX-ACCESS read-only
        STATUS current

        ::= { ebnSearchEntry 3 }

   ebnSearchSNVC OBJECT-TYPE
        SYNTAX Unsigned32
        MAX-ACCESS read-only
        STATUS current

        ::= { ebnSearchEntry 4 }


   hbn                     OBJECT IDENTIFIER ::= { ebnObjects 6 }

   hbnIsInTable OBJECT-TYPE
        SYNTAX SEQUENCE OF HbnIsInEntry
        MAX-ACCESS not-accessible
        STATUS current





        ::= { hbn 1}

   hbnIsInEntry OBJECT-TYPE
        SYNTAX HbnIsInEntry
        MAX-ACCESS not-accessible
        STATUS current

        INDEX { hbnIsInFqCpName,
                hbnIsInPcid }

   ::= { hbnIsInTable 1 }

   HbnIsInEntry ::= SEQUENCE {
           hbnIsInFqCpName    SnaControlPointName,
           hbnIsInPcid        OCTET STRING,
           hbnIsInRtpNceId    OCTET STRING,
           hbnIsInRtpTcid     OCTET STRING }

   hbnIsInFqCpName OBJECT-TYPE
        SYNTAX SnaControlPointName
        MAX-ACCESS not-accessible
        STATUS current





        ::= { hbnIsInEntry 1 }

   hbnIsInPcid OBJECT-TYPE
        SYNTAX OCTET STRING (SIZE(8))
        MAX-ACCESS not-accessible
        STATUS current

        ::= { hbnIsInEntry 2 }

   hbnIsInRtpNceId OBJECT-TYPE
        SYNTAX OCTET STRING (SIZE(1..8))
        MAX-ACCESS read-only
        STATUS current

        ::= { hbnIsInEntry 3 }

   hbnIsInRtpTcid OBJECT-TYPE
        SYNTAX OCTET STRING (SIZE(8))
        MAX-ACCESS read-only
        STATUS current

        ::= { hbnIsInEntry 4 }

   ebnConformance          OBJECT IDENTIFIER ::= { ebnMIB 2 }

   ebnCompliances          OBJECT IDENTIFIER ::= { ebnConformance 1 }
   ebnGroups               OBJECT IDENTIFIER ::= { ebnConformance 2 }

   ebnCompliance     MODULE-COMPLIANCE





     STATUS current

     MODULE   -- this module

         MANDATORY-GROUPS {
                   ebnDirectoryGroup,
                   ebnIsRscvGroup,
                   ebnDirectoryConfigGroup,
                   ebnCosMappingGroup,
                   ebnSubnetRoutingListGroup }

        GROUP hbnIsInGroup

        ::= {ebnCompliances 1 }

   ebnDirectoryGroup OBJECT-GROUP
        OBJECTS { ebnDirSubnetAffiliation }
        STATUS current

        ::= { ebnGroups 1 }


   ebnIsRscvGroup OBJECT-GROUP
        OBJECTS { ebnIsRscvDestinationRoute,
                  ebnIsRscvDestinationCos }
        STATUS current

        ::= { ebnGroups 2 }

   ebnDirectoryConfigGroup OBJECT-GROUP
        OBJECTS { ebnSearchCacheTime,
                  ebnMaxSearchCache,
                  ebnDefaultSubnetVisitCount }
        STATUS current






        ::= { ebnGroups 3 }

   ebnCosMappingGroup OBJECT-GROUP
        OBJECTS {  ebnCosMapNativeCos }
        STATUS current

        ::= { ebnGroups 4 }

   ebnSubnetRoutingListGroup OBJECT-GROUP
        OBJECTS { ebnSubnetSearchDynamics,
                  ebnSubnetSearchOrdering,
                  ebnSearchCpName,
                   ebnSearchSNVC }
        STATUS current

        ::= { ebnGroups 5 }

   hbnIsInGroup OBJECT-GROUP
        OBJECTS { hbnIsInRtpNceId, hbnIsInRtpTcid }
        STATUS current

        ::= { ebnGroups 6 }

  END
